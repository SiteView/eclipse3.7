LOAD-BAL-SYSTEM-MIB DEFINITIONS ::= BEGIN
--================================================================
--  LOAD-BAL-SYSTEM-MIB
--    A private enterprise MIB for IP load balancing systems.
--================================================================

IMPORTS
    OBJECT-TYPE, NOTIFICATION-TYPE, MODULE-IDENTITY,
    Integer32, Opaque, enterprises, Counter32, Counter64
        FROM SNMPv2-SMI

    TEXTUAL-CONVENTION, DisplayString, TruthValue
        FROM SNMPv2-TC;

--================================================================
f5 MODULE-IDENTITY
    LAST-UPDATED "200209240000Z"
    ORGANIZATION "F5 Networks, Inc."
    CONTACT-INFO
	"F5 Networks, Inc. 401 Elliot Ave. West, (206) 272-5555, support@f5.com

         postal:    F5 Networks, Inc. 
		    401 Elliot Ave. West, WA 98019
         phone:     (206) 272-5555
         email:     support@f5.com"
    DESCRIPTION
        "This file defines the private F5 SNMP MIB extensions."
    ::= { enterprises  3375 }

-- numerical definitions:
f5systems	OBJECT IDENTIFIER ::= { f5 1 }
loadbal		OBJECT IDENTIFIER ::= { f5systems 1 }

globals		OBJECT IDENTIFIER ::= { loadbal 1 }

virtualAddress	OBJECT IDENTIFIER ::= { loadbal 2 }
virtualServer	OBJECT IDENTIFIER ::= { loadbal 3 }
snat		OBJECT IDENTIFIER ::= { loadbal 4 }
interface	OBJECT IDENTIFIER ::= { loadbal 5 }
ifaddress	OBJECT IDENTIFIER ::= { loadbal 6 } -- This table is deprecated. The selfIP table will take its place
pool		OBJECT IDENTIFIER ::= { loadbal 7 }
poolMember	OBJECT IDENTIFIER ::= { loadbal 8 }
sslProxy	OBJECT IDENTIFIER ::= { loadbal 9 }
vlan		OBJECT IDENTIFIER ::= { loadbal 10 }
selfIP		OBJECT IDENTIFIER ::= { loadbal 11 }
trunk		OBJECT IDENTIFIER ::= { loadbal 12 }
nodes           OBJECT IDENTIFIER ::= { loadbal 13 }

-- Old groups
vaddress	OBJECT IDENTIFIER ::= { loadbal 100 } -- deprecated
ndaddr		OBJECT IDENTIFIER ::= { loadbal 101 }
nat		OBJECT IDENTIFIER ::= { loadbal 102 }
vport		OBJECT IDENTIFIER ::= { loadbal 103 }
member		OBJECT IDENTIFIER ::= { loadbal 104 } -- deprecated

loadBalTrap       OBJECT IDENTIFIER ::= { loadbal 110 }
loadBalTrapMsgs   OBJECT IDENTIFIER ::= { loadBalTrap 1 }
loadBalTraps      OBJECT IDENTIFIER ::= { loadBalTrap 2 }

globalAttributes OBJECT IDENTIFIER ::= { globals 1 }
globalStats	OBJECT IDENTIFIER ::= { globals 2 }

--================================================================
BigAPIStatus ::= INTEGER
{
   unchecked(0),	-- enabled node that is not monitored
   up(1), 		-- enabled node when its monitors succeed
   down(2), 		-- enabled node when its monitors fail
   forcedDown(3),  	-- node forced down manually
   checking(4), 	-- initial monitor state, thereby node state until monitor reports
   maintenance(5), 	-- always the status when bigip.maint_mode_off=0
   enabled(6), 		-- status of any object but a node that is enabled and all related objects are enabled
   disabled(7),  	-- the status of an object that is disabled
   addressDisabled(8),	-- status of any object that is enabled, but whose address is disabled
   portDisabled(9),  	-- status of any object that is enabled, but whose port is disabled
   addressDown(10)  	-- node server status if its node addr is down
}

--================================================================
--  globalAttributes
--================================================================

globalAttrKernelVersion OBJECT-TYPE
	SYNTAX DisplayString (SIZE (0..255))
	MAX-ACCESS read-only
	STATUS current 
	DESCRIPTION
	"The kernel version identifier."
	::= { globalAttributes 1 }

globalAttrPackageVersion OBJECT-TYPE
	SYNTAX DisplayString (SIZE (0..255))
	MAX-ACCESS read-only
	STATUS current
	DESCRIPTION
	"The package version."
	::= { globalAttributes 2 }

globalAttrPackageEdition OBJECT-TYPE
	SYNTAX DisplayString (SIZE (0..255))
	MAX-ACCESS read-only
	STATUS current
	DESCRIPTION
	"The package edition."
	::= { globalAttributes 3 }

globalAttrAgentVersion OBJECT-TYPE
	SYNTAX DisplayString (SIZE (0..255))
	MAX-ACCESS read-only
	STATUS deprecated
	DESCRIPTION
	"This OID has been deprecated."
	::= { globalAttributes 4 }

globalAttrProductCode OBJECT-TYPE
	SYNTAX INTEGER {
		indeterminate(1),
		ha(2),
		lb(3),
		threedns(4),
		flb(5),
		clb(6),
		xlb(7),
		ssl(8),
		test(10),
		unsupported(99)
	}
	MAX-ACCESS read-only
	STATUS current
	DESCRIPTION
	"The product identifier, possible values are HA, LB, 3-DNS, CLB, 
         FLB, XLB, and SSL."
	::= { globalAttributes 5 }

globalAttrSerialNumber OBJECT-TYPE
	SYNTAX DisplayString (SIZE (0..255))
	MAX-ACCESS read-only
	STATUS current
	DESCRIPTION
	"The serial number of this system."
	::= { globalAttributes 6 }

globalAttrVendorName OBJECT-TYPE
	SYNTAX DisplayString (SIZE (0..255))
	MAX-ACCESS read-only
	STATUS current
	DESCRIPTION
	"The name of the vendor of this system."
	::= { globalAttributes 7 }

globalAttrSSLGatewayLevel OBJECT-TYPE
	SYNTAX INTEGER {
		none(1),
		tps200(3),
		tps400(4),
		tps600(5),
		tps800(6),
		tps1000(7),
		tps500(9),
		tps1500(10),
		tps2000(11),
		unsupported(99)
	}
	MAX-ACCESS read-only
	STATUS current
	DESCRIPTION
	"This value has been deprecated - see globalAttrSslTps. 
	An integer describing transactions per second for the gateway.
	This OID does not apply to 3-DNS."
	::= { globalAttributes 8 }

globalAttrCPUCount OBJECT-TYPE
	SYNTAX INTEGER
	MAX-ACCESS read-only
	STATUS current
	DESCRIPTION
	"Total number of CPUs in this system."
	::= { globalAttributes 9 }

globalAttrAuthorized OBJECT-TYPE
	SYNTAX INTEGER { true(1), false(2) }
	MAX-ACCESS read-only
	STATUS deprecated
	DESCRIPTION
		"This OID is deprecated."
	::= { globalAttributes 10 }

globalAttrMaintenceMode OBJECT-TYPE
	SYNTAX INTEGER { true(1), false(2), unsupported(99) }
	MAX-ACCESS read-only
	STATUS current
	DESCRIPTION
	"Describes whether this system is in maintenance mode; true = Yes, 
	false = No."
	::= { globalAttributes 11 }

globalAttrMaster OBJECT-TYPE
	SYNTAX INTEGER { true(1), false(2), unsupported(99) }
	MAX-ACCESS read-only
	STATUS current
	DESCRIPTION
	"Describes fail-over state of this system; true = active, false = 
	standby."
	::= { globalAttributes 12 }

globalAttrUnitID OBJECT-TYPE
	SYNTAX DisplayString (SIZE (0..255))
	MAX-ACCESS read-only
	STATUS current
	DESCRIPTION
	"In a redundant system, the current unit identifier of this system."
	::= { globalAttributes 13 }

globalAttrPeerUnitID OBJECT-TYPE
	SYNTAX DisplayString (SIZE (0..255))
	MAX-ACCESS read-only
	STATUS current
	DESCRIPTION
	"In a redundant system, the peer's unit identifier."
	::= { globalAttributes 14 }

globalAttrFastestMaxIdleTime OBJECT-TYPE
	SYNTAX INTEGER
	MAX-ACCESS read-only
	STATUS current
	DESCRIPTION
	"A maximum time value used for load balancing to the fastest node.
	This OID does not apply to 3-DNS."
	::= { globalAttributes 15 }

globalAttrFastFlowActive OBJECT-TYPE
	SYNTAX INTEGER
	MAX-ACCESS read-only
	STATUS current
	DESCRIPTION
	"Current fast flow state: possible values include off, on, 
         and auto. This OID does not apply to 3-DNS."
	::= { globalAttributes 16 }

globalAttrGatewayFailsafeArmed OBJECT-TYPE
	SYNTAX INTEGER { true(1), false(2), unsupported(99) }
	MAX-ACCESS read-only
	STATUS current
	DESCRIPTION
	"Gateway failsafe feature; true = armed."
	::= { globalAttributes 17 }

globalAttrMemoryRebootPercent OBJECT-TYPE
	SYNTAX INTEGER
	MAX-ACCESS read-only
	STATUS current
	DESCRIPTION
	"The percentage of memory available, which will reboot the system."
	::= { globalAttributes 18 }

globalAttrMirrorEnabled OBJECT-TYPE
	SYNTAX INTEGER { true(1), false(2), unsupported(99) }
	MAX-ACCESS read-only
	STATUS current
	DESCRIPTION
	"Describes the state of mirroring; true = enabled, false = disabled."
	::= { globalAttributes 19 }

globalAttrVerboseLogLevel OBJECT-TYPE
	SYNTAX INTEGER
	MAX-ACCESS read-only
	STATUS current
	DESCRIPTION
	"A value describing the log level of error messages."
	::= { globalAttributes 20 }

globalAttrWatchDogArmed OBJECT-TYPE
	SYNTAX INTEGER { true(1), false(2), unsupported(99) }
	MAX-ACCESS read-only
	STATUS current
	DESCRIPTION
	"Describes the state of watch dog; true = armed, false = disarmed."
	::= { globalAttributes 21 }

globalAttrAutoLastHop OBJECT-TYPE
	SYNTAX INTEGER { true(1), false(2), unsupported(99) }
	MAX-ACCESS read-only
	STATUS current
	DESCRIPTION
	"Describes the behavior of last hop pools.
	This OID does not apply to 3-DNS."
	::= { globalAttributes 22 }

globalAttrAkamaiConfigPort OBJECT-TYPE
	SYNTAX INTEGER
	MAX-ACCESS read-only
	STATUS current
	DESCRIPTION
	"A port number of the Akamai feature used for configuration.
	This OID does not apply to 3-DNS."
	::= { globalAttributes 23 }

globalAttrNameSurferWebPort OBJECT-TYPE
	SYNTAX INTEGER
	MAX-ACCESS read-only
	STATUS current
	DESCRIPTION
	"Port number for NameSurfer web access."
	::= { globalAttributes 24 }

globalAttrNameSurferZonePort OBJECT-TYPE
	SYNTAX INTEGER
	MAX-ACCESS read-only
	STATUS current
	DESCRIPTION
	"Port number for NameSurfer zone access."
	::= { globalAttributes 25 }

globalAttrOpen3DNSPorts OBJECT-TYPE
	SYNTAX INTEGER { true(1), false(2), unsupported(99)}
	MAX-ACCESS read-only
	STATUS current
	DESCRIPTION
	"States whether 3-DNS ports are open; true = open, false = 
	not open."
	::= { globalAttributes 26 }

globalAttrOpenCorbaPorts OBJECT-TYPE
	SYNTAX INTEGER { true(1), false(2), unsupported(99)}
	MAX-ACCESS read-only
	STATUS current
	DESCRIPTION
	"States whether Corba ports are open for traffic; true = open,
	false = not open."
	::= { globalAttributes 27 }

globalAttrOpenFTPPorts OBJECT-TYPE
	SYNTAX INTEGER { true(1), false(2), unsupported(99)}
	MAX-ACCESS read-only
	STATUS current
	DESCRIPTION
	"States whether FTP ports are open for traffic; true = open,
	false = not open."
	::= { globalAttributes 28 }

globalAttrOpenRSHPorts OBJECT-TYPE
	SYNTAX INTEGER { true(1), false(2), unsupported(99)}
	MAX-ACCESS read-only
	STATUS current
	DESCRIPTION
	"States whether RSH ports are open for traffic; true = open,
	false = not open."
	::= { globalAttributes 29 }

globalAttrOpenSSHPorts OBJECT-TYPE
	SYNTAX INTEGER { true(1), false(2), unsupported(99)}
	MAX-ACCESS read-only
	STATUS current
	DESCRIPTION
	"States whether SSH port is open for traffic; true = open,
	false = not open."
	::= { globalAttributes 30 }

globalAttrOpenTelnetPorts OBJECT-TYPE
	SYNTAX INTEGER { true(1), false(2), unsupported(99)}
	MAX-ACCESS read-only
	STATUS current
	DESCRIPTION
	"States whether telnet port is open for traffic; true = open,
	false = not open."
	::= { globalAttributes 31 }

globalAttrWebAdminPort OBJECT-TYPE
	SYNTAX INTEGER
	MAX-ACCESS read-only
	STATUS current
	DESCRIPTION
	"Port number for web administration access."
	::= { globalAttributes 32 }

globalAttrPersistAcrossServices OBJECT-TYPE
	SYNTAX INTEGER { true(1), false(2), unsupported(99) }
	MAX-ACCESS read-only
	STATUS current
	DESCRIPTION
	"States whether all simple persistent connections from a 
         client IP address that go to the same virtual address 
         go to the same node; true = same node, false = same node not
	 guaranteed. This OID does not apply to 3-DNS."
	::= { globalAttributes 33 }

globalAttrPersistAccrossVirtuals OBJECT-TYPE
	SYNTAX INTEGER { true(1), false(2), unsupported(99) }
	MAX-ACCESS read-only
	STATUS current
	DESCRIPTION
	"States whether all simple persistent connections from the
         client IP address are sent to the same node; true = same node,
	false = same node not guaranteed.  This OID does not apply to 3-DNS."
	::= { globalAttributes 34 }

globalAttrPersistMapProxies OBJECT-TYPE
	SYNTAX INTEGER { true(1), false(2), unsupported(99) }
	MAX-ACCESS read-only
	STATUS current
	DESCRIPTION
	"States whether AOL proxy addresses are used; true = used,
	false = not used. This OID does not apply to 3-DNS."
	::= { globalAttributes 35 }

globalAttrPersistTimerUsedAsLimit OBJECT-TYPE
	SYNTAX INTEGER { true(1), false(2), unsupported(99) }
	MAX-ACCESS read-only
	STATUS current
	DESCRIPTION
	"States whether persist timer is reset on each packet; true =
	reset, false = not reset. This OID does not apply to 3-DNS."
	::= { globalAttributes 36 }

globalAttrStickyTableLimit OBJECT-TYPE
	SYNTAX INTEGER
	MAX-ACCESS read-only
	STATUS current
	DESCRIPTION
	"The maximum number of entries allowed in the sticky table.
	This OID does not apply to 3-DNS."
	::= { globalAttributes 37 }

globalAttrSNATConnLimit OBJECT-TYPE
	SYNTAX INTEGER
	MAX-ACCESS read-only
	STATUS current
	DESCRIPTION
	"A global SNAT connection limit, if zero then unlimited connections.
	This OID does not apply to 3-DNS."
	::= { globalAttributes 38 }

globalAttrSNATTCPIdleTimeout OBJECT-TYPE
	SYNTAX INTEGER
	MAX-ACCESS read-only
	STATUS current
	DESCRIPTION
	"SNAT global TCP timeout value in seconds.
	This OID does not apply to 3-DNS."
	::= { globalAttributes 39 }

globalAttrSNATUDPIdleTimeout OBJECT-TYPE
	SYNTAX INTEGER
	MAX-ACCESS read-only
	STATUS current
	DESCRIPTION
	"SNAT global UDP timeout value in seconds.
	This OID does not apply to 3-DNS."
	::= { globalAttributes 40 }

globalAttrSystemType OBJECT-TYPE
	SYNTAX INTEGER {
		serverAppliance(1),
		d25(2),
		d30(3),
		f35(4),
		dell(5),
		d35(6),
		applicationSwitch(7),
		d50(8),
		d45(9),
		unsupported(99)
	}
	MAX-ACCESS read-only
	STATUS current
	DESCRIPTION
	"Hardware type of this system."
	::= { globalAttributes 41 }

globalAttrNetReboot OBJECT-TYPE
	SYNTAX INTEGER { 
		true(1),
		false(2),
		notAvailable(3)
	}
	MAX-ACCESS read-only
	STATUS current
	DESCRIPTION
	"States whether this system will attempt a
	network reboot first; true = attempt network reboot, 
	false = do not attempt network reboot,
	notAvailable = network reboot is not available on this platform."
	::= { globalAttributes 42 }

globalAttrQuietBoot OBJECT-TYPE
	SYNTAX INTEGER {true(1), false(2), unsupported(99)}
	MAX-ACCESS read-only
	STATUS current
	DESCRIPTION
	"States whether boot messages will be suppressed during 
	a reboot of this system; true = quiet, false = not quiet."
	::= { globalAttributes 43 }

globalAttrL2CacheTimeout OBJECT-TYPE
	SYNTAX INTEGER 
	MAX-ACCESS read-only
	STATUS current
	DESCRIPTION
	"The layer 2 cache timeout value for this BIG-IP in seconds.
	This OID does not apply to 3-DNS."
	::= { globalAttributes 44 }

globalAttrSSLProxyFailOver OBJECT-TYPE
	SYNTAX INTEGER {true(1), false(2), unsupported(99)}
	MAX-ACCESS read-only
	STATUS current
	DESCRIPTION
	"States whether this BIG-IP will fail over on a fatal 
	crypto accelerator error; true = fail over, false = do not fail over.
	This OID does not apply to 3-DNS."
	::= { globalAttributes 45 }

globalAttrAkamaiConfigFile OBJECT-TYPE
	SYNTAX 	DisplayString (SIZE (0..255))
	MAX-ACCESS read-only
	STATUS current
	DESCRIPTION
	"The file path for the Akamai configuration file on this BIG-IP.
	This OID does not apply to 3-DNS."
	::= { globalAttributes 46 }

globalAttrSSLProxyServerSessionTimeout OBJECT-TYPE
	SYNTAX INTEGER
	MAX-ACCESS read-only
	STATUS current
	DESCRIPTION
	"The session cache timeout value in seconds that proxyd will use for
	its server-side session cache. This will be set to the same value used
	by back-end servers for server-side SSL connections from the
	proxy. This OID does not apply to 3-DNS."
	::= { globalAttributes 47 }

globalAttrSSLProxyServerSessionCacheSize OBJECT-TYPE
	SYNTAX 	INTEGER
	MAX-ACCESS read-only
	STATUS current
	DESCRIPTION
	"The maximum session cache size that proxyd will use for the server-side
	session cache. This OID does not apply to 3-DNS."
	::= { globalAttributes 48 }

globalAttrIPForwarding OBJECT-TYPE
	SYNTAX 	INTEGER {true(1), false(2), unsupported(99)}
	MAX-ACCESS read-only
	STATUS current
	DESCRIPTION
	"States whether unknown packets will be forwarded to the 
	gateway; true = forward, false = do not forward.
	This OID does not apply to 3-DNS."
	::= { globalAttributes 49 }

globalAttrSSLProxyUncleanShutdown OBJECT-TYPE
	SYNTAX 	INTEGER {true(1), false(2), unsupported(99)}
	MAX-ACCESS read-only
	STATUS current
	DESCRIPTION
	"Should the SSL proxy shut down SSL connections uncleanly (closing TCP connection without exchanging SSL shutdown alerts)? This OID does not apply to 3-DNS."
	::= { globalAttributes 50 }

globalAttrSSLProxyStrictResume OBJECT-TYPE
	SYNTAX 	INTEGER {true(1), false(2), unsupported(99)}
	MAX-ACCESS read-only
	STATUS current
	DESCRIPTION
	"Should the SSL proxy disallow SSL sessions to be resumed when the corresponding connection was shut down uncleanly?  This OID does not apply to 3-DNS."
	::= { globalAttributes 51 }

globalAttrSelfConnTimeout OBJECT-TYPE
	SYNTAX 	INTEGER
	MAX-ACCESS read-only
	STATUS current
	DESCRIPTION
	"Timeout for connection tracking of self traffic.  This OID does not apply to 3-DNS."
	::= { globalAttributes 52 }
	
globalAttrFailoverPort OBJECT-TYPE
	SYNTAX INTEGER { true(1), false(2), unsupported(99)}
	MAX-ACCESS read-only
	STATUS current
	DESCRIPTION
	"States whether failover port is open for traffic; true = open,
	false = not open."
	::= { globalAttributes 53 }

globalAttrSslTps OBJECT-TYPE
	SYNTAX INTEGER
	MAX-ACCESS	read-only
	STATUS	current
	DESCRIPTION
	"Transacions per second authorized for this server."
	::= { globalAttributes 54 }

globalAttrMirrorVLANForwarding OBJECT-TYPE
	SYNTAX INTEGER { true(1), false(2), unsupported(99)}
	MAX-ACCESS read-only
	STATUS current
	DESCRIPTION
		"Should unknown packets from a mirror-to vlan be forwarded?"
	::= { globalAttributes 55 }


--================================================================
--  globalStats
--================================================================



globalStatUptime OBJECT-TYPE
	SYNTAX INTEGER
	MAX-ACCESS read-only
	STATUS current
	DESCRIPTION
	"Total uptime since last reboot, in seconds."
	::= { globalStats 1 }

globalStatBitsin OBJECT-TYPE
	SYNTAX Counter32
	MAX-ACCESS read-only
	STATUS current
	DESCRIPTION
	"Total bits read off the network."
	::= { globalStats 2 }

globalStatBitsinHi32 OBJECT-TYPE
	SYNTAX Counter32
	MAX-ACCESS read-only
	STATUS current
	DESCRIPTION
	"Total bits in. (High order 32)."
	::= { globalStats 3 }

globalStatBitsout OBJECT-TYPE
	SYNTAX Counter32
	MAX-ACCESS read-only
	STATUS current
	DESCRIPTION
	"Total of all bits written to the network."
	::= { globalStats 4 }

globalStatBitsoutHi32 OBJECT-TYPE
	SYNTAX Counter32
	MAX-ACCESS read-only
	STATUS current
	DESCRIPTION
	"Total bits out. (High order 32)"
	::= { globalStats 5 }

globalStatPcktsin OBJECT-TYPE
	SYNTAX Counter32
	MAX-ACCESS read-only
	STATUS current
	DESCRIPTION
	"Total of all packets read off the network."
	::= { globalStats 6 }

globalStatPcktsinHi32 OBJECT-TYPE
	SYNTAX Counter32
	MAX-ACCESS read-only
	STATUS current
	DESCRIPTION
	"Total packets in. (High Order 32)"
	::= { globalStats 7 }

globalStatPcktsout OBJECT-TYPE
	SYNTAX Counter32
	MAX-ACCESS read-only
	STATUS current
	DESCRIPTION
	"Total of all packets written to the network."
	::= { globalStats 8 }

globalStatPcktsoutHi32 OBJECT-TYPE
	SYNTAX Counter32
	MAX-ACCESS read-only
	STATUS current
	DESCRIPTION
	"Total packets out. (High order 32)."
	::= { globalStats 9 }

globalStatCurrentConn OBJECT-TYPE
	SYNTAX Counter32
	MAX-ACCESS read-only
	STATUS current
	DESCRIPTION
	"Total current connections active."
	::= { globalStats 10 }

globalStatMaxConn OBJECT-TYPE
	SYNTAX Counter32
	MAX-ACCESS read-only
	STATUS current
	DESCRIPTION
	"Maximum number of active connections allowed."
	::= { globalStats 11 }

globalStatTotalConn OBJECT-TYPE
	SYNTAX Counter32
	MAX-ACCESS read-only
	STATUS current
	DESCRIPTION
	"Total number of connections this balancer has serviced."
	::= { globalStats 12 }

globalStatTimeouts OBJECT-TYPE
	SYNTAX Counter32
	MAX-ACCESS read-only
	STATUS current
	DESCRIPTION
        "Total number of timeouts for this object."
	::= { globalStats 13 }

globalStatMemoryPoolTotal OBJECT-TYPE
	SYNTAX INTEGER
	MAX-ACCESS read-only
	STATUS current
	DESCRIPTION
	"Total memory pool available on system."
	::= { globalStats 14 }

globalStatMemoryPoolUsed OBJECT-TYPE
	SYNTAX INTEGER
	MAX-ACCESS read-only
	STATUS current
	DESCRIPTION
	"Total memory pool currently in use by system."
	::= { globalStats 15 }

globalStatStandBySharedDrop OBJECT-TYPE
	SYNTAX Counter32
	MAX-ACCESS read-only
	STATUS current
	DESCRIPTION
	"Total number of packets, destined for shared address, but received 
	on standby system."
	::= { globalStats 16 }

globalStatSelfTCPPortDeny OBJECT-TYPE
	SYNTAX Counter32
	MAX-ACCESS read-only
	STATUS current
	DESCRIPTION
	"Total number of TCP port denials for all self IP addresses."
	::= { globalStats 17 }

globalStatSelfUDPPortDeny OBJECT-TYPE
	SYNTAX Counter32
	MAX-ACCESS read-only
	STATUS current
	DESCRIPTION
	"Total number of UDP port denials for all self IP addresses."
	::= { globalStats 18 }

globalStatMaintenanceModeDeny OBJECT-TYPE
	SYNTAX Counter32
	MAX-ACCESS read-only
	STATUS current
	DESCRIPTION
	"Total number of attempts to deny maintenance mode."
	::= { globalStats 19 }

globalStatVirtualServerUDPPortDeny OBJECT-TYPE
	SYNTAX Counter32
	MAX-ACCESS read-only
	STATUS current
	DESCRIPTION
	"Total number of UDP port denials for all virtual addresses.
	This OID does not apply to 3-DNS."
	::= { globalStats 20 }

globalStatVirtualServerTCPPortDeny OBJECT-TYPE
	SYNTAX Counter32
	MAX-ACCESS read-only
	STATUS current
	DESCRIPTION
	"Total number of TCP port denials for all virtual servers.
	This OID does not apply to 3-DNS."
	::= { globalStats 21 }

globalStatVirtualServerDupSynSSL OBJECT-TYPE
	SYNTAX Counter32
	MAX-ACCESS read-only
	STATUS current
	DESCRIPTION
	"Total number of duplicate SYNs for SSL traffic.
	This OID does not apply to 3-DNS."
	::= { globalStats 22 }

globalStatVirtualServerDupSynWrongDest OBJECT-TYPE
	SYNTAX Counter32
	MAX-ACCESS read-only
	STATUS current
	DESCRIPTION
	"Total number of duplicate SYNs for virtual servers, sent to the 
         wrong destination. This OID does not apply to 3-DNS."
	::= { globalStats 23 }

globalStatVirtualServerDupSynNodeDown OBJECT-TYPE
	SYNTAX Counter32
	MAX-ACCESS read-only
	STATUS current
	DESCRIPTION
	"Total number of duplicate SYNs for virtual servers, sent to down node.
	This OID does not apply to 3-DNS."
	::= { globalStats 24 }

globalStatVirtualServerNonSynDeny OBJECT-TYPE
	SYNTAX Counter32
	MAX-ACCESS read-only
	STATUS current
	DESCRIPTION
	"Total number of non SYN denials, for all virtual servers.
	This OID does not apply to 3-DNS."
	::= { globalStats 25 }

globalStatMaxConnPortDeny OBJECT-TYPE
	SYNTAX Counter32
	MAX-ACCESS read-only
	STATUS current
	DESCRIPTION
	"Total number of connections denied because maximum connections 
         count exceeded. This OID does not apply to 3-DNS."
	::= { globalStats 26 }

globalStatMaxConnVirtualAddressDeny OBJECT-TYPE
	SYNTAX Counter32
	MAX-ACCESS read-only
	STATUS current
	DESCRIPTION
	"Total number of connections denied to all virtual addresses, 
         because  maximum connections exceeded.
	This OID does not apply to 3-DNS."
	::= { globalStats 27 }

globalStatMaxConnVirtualPathDeny OBJECT-TYPE
	SYNTAX Counter32
	MAX-ACCESS read-only
	STATUS current
	  DESCRIPTION
	"Total number of connections denied to all virtual servers, 
         because maximum connections exceeded.
	This OID does not apply to 3-DNS."
	::= { globalStats 28 }

globalStatVirtualServerFragNoPort OBJECT-TYPE
	SYNTAX Counter32
	MAX-ACCESS read-only
	STATUS current
	DESCRIPTION
	"Total number of fragments, sent to virtual servers, with no port.
	This OID does not apply to 3-DNS."
	::= { globalStats 29 }

globalStatVirtualServerFragNoConn OBJECT-TYPE
	SYNTAX Counter32
	MAX-ACCESS read-only
	STATUS current
	DESCRIPTION
	"Total number of fragments, sent to virtual servers, with no connection.
	This OID does not apply to 3-DNS."
	::= { globalStats 30 }

globalStatNoHandlerDeny OBJECT-TYPE
	SYNTAX Counter32
	MAX-ACCESS read-only
	STATUS current
	DESCRIPTION
	"Total number of handler denials."
	::= { globalStats 31 }

globalStatTCPTimeouts OBJECT-TYPE
	SYNTAX Counter32
	MAX-ACCESS read-only
	STATUS current
	DESCRIPTION
	"Total number of TCP timeouts."
	::= { globalStats 32 }

globalStatUDPTimeouts OBJECT-TYPE
	SYNTAX Counter32
	MAX-ACCESS read-only
	STATUS current
	DESCRIPTION
	"Total number of UDP timeouts."
	::= { globalStats 33 }

globalStatIPTimeouts OBJECT-TYPE
	SYNTAX Counter32
	MAX-ACCESS read-only
	STATUS current
	DESCRIPTION
	"Total number of IP timeouts."
	::= { globalStats 34 }

globalStatSSLTimeouts OBJECT-TYPE
	SYNTAX Counter32
	MAX-ACCESS read-only
	STATUS current
	DESCRIPTION
	"Total number of SSL timeouts. This OID does not apply to 3-DNS."
	::= { globalStats 35 }

globalStatPersistTimeouts OBJECT-TYPE
	SYNTAX Counter32
	MAX-ACCESS read-only
	STATUS current
	DESCRIPTION
	"Total number of persistence timeouts."
	::= { globalStats 36 }

globalStatMultiProcessorMode OBJECT-TYPE
	SYNTAX INTEGER
	MAX-ACCESS read-only
	STATUS current
	DESCRIPTION
	"Current multiprocessing mode; UP is the uniprocessor mode. 
	 ANIP is the auxiliary network interface mode. SMP is the symmetric
	multiprocessor mode."
	::= { globalStats 37 }

globalStatCPUCount OBJECT-TYPE
	SYNTAX INTEGER
	MAX-ACCESS read-only
	STATUS current
	DESCRIPTION
	"Total number of CPUs."
	::= { globalStats 38 }

globalStatActiveCPUCount OBJECT-TYPE
	SYNTAX INTEGER
	MAX-ACCESS read-only
	STATUS current
	DESCRIPTION
	"Total number of currently active CPUs."
	::= { globalStats 39 }

globalStatANIPPercent OBJECT-TYPE
	SYNTAX INTEGER
	MAX-ACCESS read-only
	STATUS current
	DESCRIPTION
	"Total percent of CPU devoted to ANIP feature."
	::= { globalStats 40 }

globalStatMaxANIPPercent OBJECT-TYPE
	SYNTAX INTEGER
	MAX-ACCESS read-only
	STATUS current
	DESCRIPTION
	"Maximum percent of CPU devoted to ANIP feature, since last reboot."
	::= { globalStats 41 }

globalStatMemoryErrors OBJECT-TYPE
	SYNTAX Counter32
	MAX-ACCESS read-only
	STATUS current
	DESCRIPTION
	"Total number of memory allocation errors."
	::= { globalStats 42 }

globalStatNoNodeErrors OBJECT-TYPE
	SYNTAX Counter32
	MAX-ACCESS read-only
	STATUS current
	DESCRIPTION
	"If active member count is zero, then this counter is incremented."
	::= { globalStats 43 }

globalStatMemoryInUse OBJECT-TYPE
	SYNTAX INTEGER
	MAX-ACCESS read-only
	STATUS current
	DESCRIPTION
	"Current amount of memory in use."
	::= { globalStats 44 }

globalStatMemoryMaxUsed OBJECT-TYPE
	SYNTAX INTEGER
	MAX-ACCESS read-only
	STATUS current
	DESCRIPTION
	"Maximum amount of memory used since last reboot."
	::= { globalStats 45 }

globalStatMemoryCurrentSize OBJECT-TYPE
	SYNTAX INTEGER
	MAX-ACCESS read-only
	STATUS current
	DESCRIPTION
	"Current memory size."
	::= { globalStats 46 }

globalStatCPUTemperature OBJECT-TYPE
	SYNTAX INTEGER
	MAX-ACCESS read-only
	STATUS deprecated
	DESCRIPTION
		"This OID is deprecated -- see Platform MIB."
	::= { globalStats 47 }

globalStatFanSpeed OBJECT-TYPE
	SYNTAX INTEGER
	MAX-ACCESS read-only
	STATUS deprecated
	DESCRIPTION
		"This OID is deprecated -- see Platform MIB."
	::= { globalStats 48 }

globalStatHCBitsin OBJECT-TYPE
	SYNTAX Counter64
	MAX-ACCESS read-only
	STATUS current
	DESCRIPTION
	"Total bits read off the network."
	::= { globalStats 49 }

globalStatHCBitsout OBJECT-TYPE
	SYNTAX Counter64
	MAX-ACCESS read-only
	STATUS current
	DESCRIPTION
	"Total of all bits written to the network."
	::= { globalStats 50 }

globalStatHCPcktsin OBJECT-TYPE
	SYNTAX Counter64
	MAX-ACCESS read-only
	STATUS current
	DESCRIPTION
	"Total of all packets read off the network."
	::= { globalStats 51 }

globalStatHCPcktsout OBJECT-TYPE
	SYNTAX Counter64
	MAX-ACCESS read-only
	STATUS current
	DESCRIPTION
	"Total of all packets written to the network."
	::= { globalStats 52 }

--================================================================
-- Interfaces 
--================================================================

interfaceNumber OBJECT-TYPE
	SYNTAX INTEGER (0..65535)
	MAX-ACCESS read-only
	STATUS current
	DESCRIPTION
		"The number of interfaces on this system."
	::= { interface 1 }

interfaceTable OBJECT-TYPE
	SYNTAX SEQUENCE OF InterfaceEntry
	MAX-ACCESS not-accessible
	STATUS current
	DESCRIPTION
		"A table containing information about the system interfaces."
	::= { interface 2 }

interfaceEntry OBJECT-TYPE
	SYNTAX InterfaceEntry
	MAX-ACCESS not-accessible
	STATUS current
	DESCRIPTION
		"Columns in the Interface Table."
	INDEX { interfaceName }
	::= { interfaceTable 1 }

InterfaceEntry ::=
	SEQUENCE {
		interfaceName			DisplayString,
		interfaceIpAddresses		DisplayString,
		interfaceDestination		INTEGER,
		interfaceSource			INTEGER,
		interfaceTimeout		INTEGER, -- This variable is deprecated.
		interfaceArmed			INTEGER, -- This variable is deprecated.
		interfaceVLANSEnabled		INTEGER, -- This variable is deprecated.
		interfaceMasqueradeAddress	DisplayString,
		interfaceLastTimeChanged	INTEGER,
		interfaceSpeed			INTEGER,
		interfaceFullDuplex		INTEGER,
		interfaceMediaTypeActive	DisplayString,
		interfaceMediaDuplexActive	DisplayString,
		interfaceMediaStatus		INTEGER,
		interfaceMediaType		DisplayString,
		interfaceMediaDuplex		DisplayString,
		interfaceMTU			INTEGER
	}

interfaceName OBJECT-TYPE
	SYNTAX 	DisplayString (SIZE (0..8))
	MAX-ACCESS read-only
	STATUS current
	DESCRIPTION
		"The name of this interface. The name will be composed of the 
		slot number, followed by the port number of the interface. 
		These numbers start at 1 and the slots are numbered from left 
		to right. The ports are numbered from top to bottom."

	::= { interfaceEntry 1 }

interfaceIpAddresses OBJECT-TYPE
	SYNTAX 	DisplayString (SIZE (0..255))
	MAX-ACCESS read-only
	STATUS deprecated
	DESCRIPTION
		"This OID is deprecated. Each interface will handle IP 
		addresses based on the VLAN(s) assigned to the interface 
		and the IP addresses associated with those VLAN(s).
		This entry will always return an empty string."
	::= { interfaceEntry 2 }

interfaceDestination OBJECT-TYPE
	SYNTAX 	INTEGER {
		true(1),
		false(2)
	}
	MAX-ACCESS read-only
	STATUS deprecated
	DESCRIPTION
		"This OID is deprecated. All interfaces will always be 
		enabled for destination processing. This will always return 
		true."
	::= { interfaceEntry 3 }

interfaceSource OBJECT-TYPE
	SYNTAX 	INTEGER {
		true(1),
		false(2)
	}
	MAX-ACCESS read-only
	STATUS deprecated
	DESCRIPTION
		"This OID is deprecated. All interfaces are enabled for source 
		processing.  This will always return true."
	::= { interfaceEntry 4 }

interfaceTimeout OBJECT-TYPE
	SYNTAX 	INTEGER
	MAX-ACCESS read-only
	STATUS deprecated
	DESCRIPTION
		"This OID is deprecated. This will always return -1;
		The seconds before a failover is triggered in failsafe mode."
	::= { interfaceEntry 5 }

interfaceArmed OBJECT-TYPE
	SYNTAX 	INTEGER {
		true(1),
		false(2)
	}
	MAX-ACCESS read-only
	STATUS deprecated
	DESCRIPTION
		"This OID is deprecated. This will always return true.
		The interface will be armed if the interface failsafe mode 
		is activated."
	::= { interfaceEntry 6 }

interfaceVLANSEnabled OBJECT-TYPE
	SYNTAX 	INTEGER {
		true(1),
		false(2)
	}
	MAX-ACCESS read-only
	STATUS deprecated
	DESCRIPTION
		"This attribute is deprecated. This OID will always return true."
	::= { interfaceEntry 7 }

interfaceMasqueradeAddress OBJECT-TYPE
	SYNTAX 	DisplayString (SIZE (0..255))
	MAX-ACCESS read-only
	STATUS current
	DESCRIPTION
		"MAC masquerade address of this interface."
	::= { interfaceEntry 8 }

interfaceLastTimeChanged OBJECT-TYPE
	SYNTAX 	INTEGER
	MAX-ACCESS read-only
	STATUS current
	DESCRIPTION
		"The last time the interface attributes were modified - in seconds
		since the epoch."
	::= { interfaceEntry 9 }

interfaceSpeed OBJECT-TYPE
	SYNTAX 	INTEGER
	MAX-ACCESS read-only
	STATUS current
	DESCRIPTION
		"The speed of this interface, in Mbps."
	::= { interfaceEntry 10 }

interfaceFullDuplex OBJECT-TYPE
	SYNTAX 	INTEGER {
		true(1),
		false(2)
	}
	MAX-ACCESS read-only
	STATUS current
	DESCRIPTION
		"States whether this interface is operating in 
		full-duplex mode; true = full-duplex, false = not full-duplex."
	::= { interfaceEntry 11 }

interfaceMediaTypeActive OBJECT-TYPE
	SYNTAX 	DisplayString (SIZE (0..255))
	MAX-ACCESS read-only
	STATUS current
	DESCRIPTION
		"The currently active media type."
	::= { interfaceEntry 12 }

interfaceMediaDuplexActive OBJECT-TYPE
	SYNTAX 	DisplayString (SIZE (0..255))
	MAX-ACCESS read-only
	STATUS current
	DESCRIPTION
		"The currently active duplex mode for this interface."
	::= { interfaceEntry 13 }

interfaceMediaStatus OBJECT-TYPE
	SYNTAX 	INTEGER {
		active(1),
		nocarrier(2),
		invalid(3)
	}
	MAX-ACCESS read-only
	STATUS current
	DESCRIPTION
		"The media status for this interface."
	::= { interfaceEntry 14 }

interfaceMediaType OBJECT-TYPE
	SYNTAX 	DisplayString (SIZE (0..255))
	MAX-ACCESS read-only
	STATUS current
	DESCRIPTION
		"The preferred media type for this interface."
	::= { interfaceEntry 15 }

interfaceMediaDuplex OBJECT-TYPE
	SYNTAX 	DisplayString (SIZE (0..255))
	MAX-ACCESS read-only
	STATUS current
	DESCRIPTION
		"The preferred media duplex mode for this interface."
	::= { interfaceEntry 16 }

interfaceMTU OBJECT-TYPE
	SYNTAX 	INTEGER
	MAX-ACCESS read-only
	STATUS current
	DESCRIPTION
		"The maximum transmission unit size for this interface."
	::= { interfaceEntry 17 }

--================================================================
--  interface IP addresses 
--================================================================

ifaddressNumber OBJECT-TYPE
	SYNTAX INTEGER (0..65535)
	MAX-ACCESS read-only
	STATUS deprecated
	DESCRIPTION
		"The number of interface IP addresses on this system. This 
		table has been deprecated.  This OID will always return 0. 
		The selfIP table has taken its place. Interfaces are no
		longer directly associated with IP addresses."
	::= { ifaddress 1 }

ifaddressTable OBJECT-TYPE
	SYNTAX SEQUENCE OF IfaddressEntry
	MAX-ACCESS not-accessible
	STATUS deprecated
	DESCRIPTION
		"This table has been deprecated it will always be empty. The 
		selfIP table has taken its place. Interfaces are no longer 
		directly associated with IP addresses. They are now only
		associated with VLANs."
	::= { ifaddress 2 }

ifaddressEntry OBJECT-TYPE
	SYNTAX IfaddressEntry
	MAX-ACCESS not-accessible
	STATUS deprecated
	DESCRIPTION
		"This OID is deprecated. Columns in the Interface Table."
	INDEX { ifaddressIpAddress }
	::= { ifaddressTable 1 }

IfaddressEntry ::=
	SEQUENCE {
		ifaddressIpAddress		IpAddress,
		ifaddressInterfaceName		DisplayString,
		ifaddressNetmask		IpAddress,
		ifaddressBroadcast		IpAddress,
		ifaddressType			INTEGER,
		ifaddressUnitId			INTEGER,
		ifaddressVLANTag	        DisplayString
	}

ifaddressIpAddress OBJECT-TYPE
	SYNTAX IpAddress
	MAX-ACCESS read-only
	STATUS deprecated
	DESCRIPTION
		"This OID is deprecated. The IP address for this interface 
		IP address."
	::= { ifaddressEntry 1 }

ifaddressInterfaceName OBJECT-TYPE
	SYNTAX 	DisplayString (SIZE (0..255))
	MAX-ACCESS read-only
	STATUS deprecated
	DESCRIPTION
		"This OID is deprecated. The name of the interface for this 
		IP address."
	::= { ifaddressEntry 2 }

ifaddressNetmask OBJECT-TYPE
	SYNTAX IpAddress
	MAX-ACCESS read-only
	STATUS deprecated
	DESCRIPTION
		"This OID is deprecated. The netmask for this interface IP 
		address."
	::= { ifaddressEntry 3 }

ifaddressBroadcast OBJECT-TYPE
	SYNTAX IpAddress
	MAX-ACCESS read-only
	STATUS deprecated
	DESCRIPTION
		"This OID is deprecated. The broadcast address for this 
		interface IP address."
	::= { ifaddressEntry 4 }

ifaddressType OBJECT-TYPE
	SYNTAX INTEGER {
		iptrue(1),
		ipshared(2)
	}
	MAX-ACCESS read-only
	STATUS deprecated
	DESCRIPTION
		"This OID is deprecated. The type for this interface IP 
		address."
	::= { ifaddressEntry 5 }

ifaddressUnitId OBJECT-TYPE
	SYNTAX INTEGER
	MAX-ACCESS read-only
	STATUS deprecated
	DESCRIPTION
		"This OID is deprecated. The unit id for this interface IP 
		address."
	::= { ifaddressEntry 6 }

ifaddressVLANTag OBJECT-TYPE
	SYNTAX 	DisplayString (SIZE (0..5))
	MAX-ACCESS read-only
	STATUS deprecated
	DESCRIPTION
		"This OID is deprecated. The VLAN tag for this interface IP 
		address."
	::= { ifaddressEntry 7 }

--================================================================
--  Pools
--================================================================

poolNumber OBJECT-TYPE
	SYNTAX INTEGER (0..65535)
	MAX-ACCESS read-only
	STATUS current
	DESCRIPTION
		"The number of pools on this BIG-IP."
	::= { pool 1 }

poolTable OBJECT-TYPE
	SYNTAX SEQUENCE OF PoolEntry
	MAX-ACCESS not-accessible
	STATUS current
	DESCRIPTION
		"A table containing information about the BIG-IP pools."
	::= { pool 2 }

poolEntry OBJECT-TYPE
	SYNTAX PoolEntry
	MAX-ACCESS not-accessible
	STATUS current
	DESCRIPTION
		"Columns in the Pool Table."
	INDEX { poolName }
	::= { poolTable 1 }

PoolEntry ::=
	SEQUENCE {
		poolName		DisplayString,
		poolLBMode		INTEGER,
		poolDependent		INTEGER, -- This has been deprecated.
		poolMemberQty		INTEGER,
		poolBitsin		Counter32,
		poolBitsout		Counter32,
		poolBitsinHi32		Counter32,
		poolBitsoutHi32		Counter32,
		poolPktsin		Counter32,
		poolPktsout		Counter32,
		poolPktsinHi32		Counter32,
		poolPktsoutHi32		Counter32,
		poolMaxConn		INTEGER,
		poolCurrentConn		INTEGER,
		poolTotalConn		Counter32,
		poolPersistMode		INTEGER,
		poolSSLTimeout		INTEGER,
		poolSimpleTimeout	INTEGER,
		poolSimpleMask		IpAddress,
		poolStickyMask		IpAddress,
		poolCookieMode		INTEGER,
		poolCookieExpiration	INTEGER,
		poolCookieHashName	DisplayString,
		poolCookieHashOffset	INTEGER,
		poolCookieHashLength	INTEGER,
		poolMinActiveMembers	INTEGER,
		poolActiveMemberCount	INTEGER,
		poolPersistMirror	INTEGER,
		poolFallbackHost	DisplayString,
		poolCloneBeforePoolName DisplayString,
		poolCloneAfterPoolName DisplayString,
		poolOutOfBand 		TruthValue,
		poolHCBitsin		Counter64,
		poolHCBitsout		Counter64,
		poolHCPktsin		Counter64,
		poolHCPktsout		Counter64
	}

poolName OBJECT-TYPE
	SYNTAX DisplayString (SIZE (0..255))
	MAX-ACCESS read-only
	STATUS current
	DESCRIPTION
		"The name of this pool."
	::= { poolEntry 1 }

poolLBMode OBJECT-TYPE
	SYNTAX INTEGER {
		roundrobin(1),
		ratioMember(2),
		leastConnMember(3),
		observedMember(4),
		predictiveMember(5),
		ratioNodeAddress(6),
		leastConnNodeAddress(7),
		fastestNodeAddress(8),
		observerdNodeAddress(9),
		predictiveNodeAddress(10),
		dynamicRatio(11),
		fastestAppResponse(12)
	}
	MAX-ACCESS read-only
	STATUS current
	DESCRIPTION
		"The load balance mode of this pool."
	::= { poolEntry 2 }

poolDependent OBJECT-TYPE
	SYNTAX INTEGER {
		true(1),
		false(2)
	}
	MAX-ACCESS read-only
	STATUS deprecated
	DESCRIPTION
		"States whether this pool a dependent pool;
		true = dependent; false = not dependent.
		This OID is deprecated and will always return false."
	::= { poolEntry 3 }

poolMemberQty OBJECT-TYPE
	SYNTAX INTEGER
	MAX-ACCESS read-only
	STATUS current
	DESCRIPTION
		"The number of members in this pool."
	::= { poolEntry 4 }

poolBitsin OBJECT-TYPE
	SYNTAX 	Counter32
	MAX-ACCESS read-only
	STATUS current
	DESCRIPTION
		"The number of bits received on this pool.  If the count
		overflows a 32 bit value, this contains the lower 32 bits
		of a 64 bit counter with the upper 32 bits contained in 
		poolBitsinHi32."
	::= { poolEntry 5 }

poolBitsout OBJECT-TYPE
	SYNTAX 	Counter32
	MAX-ACCESS read-only
	STATUS current
	DESCRIPTION
		"The number of bits sent on this pool.  If the count
		overflows a 32 bit value, this contains the lower 32 bits
		of a 64 bit counter with the upper 32 bits contained in 
		poolBitsoutHi32"
	::= { poolEntry 6 }

poolBitsinHi32 OBJECT-TYPE
	SYNTAX 	Counter32
	MAX-ACCESS read-only
	STATUS current
	DESCRIPTION
		"Upper 32 bits of the poolBitsin counter."
	::= { poolEntry 7 }

poolBitsoutHi32 OBJECT-TYPE
	SYNTAX 	Counter32
	MAX-ACCESS read-only
	STATUS current
	DESCRIPTION
		"Upper 32 bits of the poolBitsout counter."
	::= { poolEntry 8 }

poolPktsin OBJECT-TYPE
	SYNTAX 	Counter32
	MAX-ACCESS read-only
	STATUS current
	DESCRIPTION
		"The number of packets received on this pool.  If the count
		overflows a 32 bit value, this contains the lower 32 bits
		of a 64 bit counter with the upper 32 bits contained in 
		poolPktsinHi32."
	::= { poolEntry 9 }

poolPktsout OBJECT-TYPE
	SYNTAX 	Counter32
	MAX-ACCESS read-only
	STATUS current
	DESCRIPTION
		"The number of packets received on this pool.  If the count
		overflows a 32 bit value, this contains the lower 32 bits
		of a 64 bit counter with the upper 32 bits contained in 
		poolPktsoutHi32."
	::= { poolEntry 10 }

poolPktsinHi32 OBJECT-TYPE
	SYNTAX 	Counter32
	MAX-ACCESS read-only
	STATUS current
	DESCRIPTION
		"Upper 32 bits of the poolPktsin counter."
	::= { poolEntry 11 }

poolPktsoutHi32 OBJECT-TYPE
	SYNTAX 	Counter32
	MAX-ACCESS read-only
	STATUS current
	DESCRIPTION
		"Upper 32 bits of the poolPktsout counter."
	::= { poolEntry 12 }

poolMaxConn OBJECT-TYPE
	SYNTAX INTEGER (0..65535)
	MAX-ACCESS read-only
	STATUS current
	DESCRIPTION
		"The maximum number of connections the members of  
		this pool have had open at any one time."
	::= { poolEntry 13 }

poolCurrentConn OBJECT-TYPE
	SYNTAX INTEGER (0..65535)
	MAX-ACCESS read-only
	STATUS current
	DESCRIPTION
		"The current number of connections the members of  
		this pool have open."
	::= { poolEntry 14 }

poolTotalConn OBJECT-TYPE
	SYNTAX Counter32
	MAX-ACCESS read-only
	STATUS current
	DESCRIPTION
		"The total number of connections the members of 
		this pool have served since the pool started."
	::= { poolEntry 15 }

poolPersistMode OBJECT-TYPE
	SYNTAX INTEGER {
		none(1),
		simple(2),
		sticky(3),
		cookie(4),
		ssl(5)
	}
	MAX-ACCESS read-only
	STATUS current
	DESCRIPTION
		"Persistence mode for this pool."
	::= { poolEntry 16 }

poolSSLTimeout OBJECT-TYPE
	SYNTAX INTEGER
	MAX-ACCESS read-only
	STATUS current
	DESCRIPTION
		"The timeout value in seconds for SSL persistence for this pool."
	::= { poolEntry 17 }

poolSimpleTimeout OBJECT-TYPE
	SYNTAX INTEGER
	MAX-ACCESS read-only
	STATUS current
	DESCRIPTION
		"The timeout value in seconds for simple persistence for this pool."
	::= { poolEntry 18 }

poolSimpleMask OBJECT-TYPE
	SYNTAX IpAddress
	MAX-ACCESS read-only
	STATUS current
	DESCRIPTION
		"The simple persistence mask for this pool."
	::= { poolEntry 19 }

poolStickyMask OBJECT-TYPE
	SYNTAX IpAddress
	MAX-ACCESS read-only
	STATUS current
	DESCRIPTION
		"The sticky persistence mask for this pool."
	::= { poolEntry 20 }

poolCookieMode OBJECT-TYPE
	SYNTAX INTEGER {
		unspecified(1),
		insert(2),
		rewrite(3),
		passive(4),
		hash(5)
	}
	MAX-ACCESS read-only
	STATUS current
	DESCRIPTION
		"Cookie mode used with cookie persistence mode."
	::= { poolEntry 21 }

poolCookieExpiration OBJECT-TYPE
	SYNTAX INTEGER
	MAX-ACCESS read-only
	STATUS current
	DESCRIPTION
		"The persistent cookie expiration time in seconds for this pool."
	::= { poolEntry 22 }

poolCookieHashName OBJECT-TYPE
	SYNTAX DisplayString (SIZE (0..255))
	MAX-ACCESS read-only
	STATUS current
	DESCRIPTION
		"The cookie hash name for this pool."
	::= { poolEntry 23 }

poolCookieHashOffset OBJECT-TYPE
	SYNTAX INTEGER
	MAX-ACCESS read-only
	STATUS current
	DESCRIPTION
		"The cookie hash offset for this pool."
	::= { poolEntry 24 }

poolCookieHashLength OBJECT-TYPE
	SYNTAX INTEGER
	MAX-ACCESS read-only
	STATUS current
	DESCRIPTION
		"The cookie hash length for this pool."
	::= { poolEntry 25 }

poolMinActiveMembers OBJECT-TYPE
	SYNTAX INTEGER
	MAX-ACCESS read-only
	STATUS current
	DESCRIPTION
		"The minimum number of active members."
	::= { poolEntry 26 }

poolActiveMemberCount OBJECT-TYPE
	SYNTAX INTEGER
	MAX-ACCESS read-only
	STATUS current
	DESCRIPTION
		"The number of currently active members for this pool."
	::= { poolEntry 27 }

poolPersistMirror OBJECT-TYPE
	SYNTAX INTEGER {
		true(1),
		false(2)
	}
	MAX-ACCESS read-only
	STATUS current
	DESCRIPTION
		"States whether this BIG-IP is set up for persistence 
		mirroring; true = persistence is mirrored, false = persistence
		is not mirrored."
	::= { poolEntry 28 }

poolFallbackHost OBJECT-TYPE
	SYNTAX DisplayString (SIZE (0..255))
	MAX-ACCESS read-only
	STATUS current
	DESCRIPTION
		"The fallback host for this pool."
	::= { poolEntry 29 }

poolCloneBeforePoolName OBJECT-TYPE
	SYNTAX DisplayString (SIZE (0..255))
	MAX-ACCESS read-only
	STATUS current
	DESCRIPTION
		""
	::= { poolEntry 30 }

poolCloneAfterPoolName OBJECT-TYPE
	SYNTAX DisplayString (SIZE (0..255))
	MAX-ACCESS read-only
	STATUS current
	DESCRIPTION
		""
	::= { poolEntry 31 }

poolOutOfBand OBJECT-TYPE
	SYNTAX TruthValue
	MAX-ACCESS read-only
	STATUS current
	DESCRIPTION
		""
	::= { poolEntry 32 }

poolHCBitsin OBJECT-TYPE
	SYNTAX Counter64
	MAX-ACCESS read-only
	STATUS current
	DESCRIPTION
		"The number of bits received on this pool."
	::= { poolEntry 33 }

poolHCBitsout OBJECT-TYPE
	SYNTAX Counter64
	MAX-ACCESS read-only
	STATUS current
	DESCRIPTION
		"The number of bits sent to this pool."
	::= { poolEntry 34 }

poolHCPktsin OBJECT-TYPE
	SYNTAX Counter64
	MAX-ACCESS read-only
	STATUS current
	DESCRIPTION
		"The number of packets received on this pool."
	::= { poolEntry 35 }

poolHCPktsout OBJECT-TYPE
	SYNTAX Counter64
	MAX-ACCESS read-only
	STATUS current
	DESCRIPTION
		"The number of packets sent to this pool."
	::= { poolEntry 36 }



--================================================================
--  Pool Members
--================================================================

poolMemberNumber OBJECT-TYPE
	SYNTAX INTEGER (0..65535)
	MAX-ACCESS read-only
	STATUS current
	DESCRIPTION
		"The number of pool members on this BIG-IP."
	::= { poolMember 1 }

poolMemberTable OBJECT-TYPE
	SYNTAX SEQUENCE OF PoolMemberEntry
	MAX-ACCESS not-accessible
	STATUS current
	DESCRIPTION
		"A table containing information about the BIG-IP pool members."
	::= { poolMember 2 }

poolMemberEntry OBJECT-TYPE
	SYNTAX PoolMemberEntry
	MAX-ACCESS not-accessible
	STATUS current
	DESCRIPTION
		"Columns in the Pool Member Table."
	INDEX { poolMemberPoolName, poolMemberIpAddress, poolMemberPort }
	::= { poolMemberTable 1 }

PoolMemberEntry ::=
	SEQUENCE {
		poolMemberPoolName		DisplayString,
		poolMemberIpAddress		IpAddress,
		poolMemberPort			INTEGER,
		poolMemberMaintenance		INTEGER,
		poolMemberRatio			INTEGER,
		poolMemberPriority		INTEGER,
		poolMemberWeight		INTEGER,
		poolMemberRipeness		INTEGER,
		poolMemberBitsin		Counter32,
		poolMemberBitsout		Counter32,
		poolMemberBitsinHi32		Counter32,
		poolMemberBitsoutHi32		Counter32,
		poolMemberPktsin		Counter32,
		poolMemberPktsout		Counter32,
		poolMemberPktsinHi32		Counter32,
		poolMemberPktsoutHi32		Counter32,
		poolMemberConnLimit		INTEGER,
		poolMemberMaxConn		INTEGER,
		poolMemberCurrentConn		INTEGER,
		poolMemberTotalConn		Counter32,
 		poolMemberStatus		BigAPIStatus,
 		poolMemberIPStatus		BigAPIStatus,
		poolMemberHCBitsin		Counter64,
		poolMemberHCBitsout		Counter64,
		poolMemberHCPktsin		Counter64,
		poolMemberHCPktsout		Counter64
	}

poolMemberPoolName OBJECT-TYPE
	SYNTAX DisplayString (SIZE (0..255))
	MAX-ACCESS read-only
	STATUS current
	DESCRIPTION
		"The name of the pool which contains this member."
	::= { poolMemberEntry 1 }

poolMemberIpAddress OBJECT-TYPE
	SYNTAX IpAddress
	MAX-ACCESS read-only
	STATUS current
	DESCRIPTION
		"The IP address of this pool member."
	::= { poolMemberEntry 2 }

poolMemberPort OBJECT-TYPE
	SYNTAX INTEGER (0..65535)
	MAX-ACCESS read-only
	STATUS current
	DESCRIPTION
		"The port of this pool member."
	::= { poolMemberEntry 3 }

poolMemberMaintenance OBJECT-TYPE
	SYNTAX INTEGER {
		true(1),
		false(2)
	}
	MAX-ACCESS read-only
	STATUS current
	DESCRIPTION
		"States whether this pool member is in maintenance 
		mode; true = maintenance mode, false = not maintenance mode."
	::= { poolMemberEntry 4 }

poolMemberRatio OBJECT-TYPE
	SYNTAX INTEGER
	MAX-ACCESS read-only
	STATUS current
	DESCRIPTION
		"Load balancing ratio of the member within the pool. 
		Used by member ratio load balancing mode."
	::= { poolMemberEntry 5 }

poolMemberPriority OBJECT-TYPE
	SYNTAX INTEGER
	MAX-ACCESS read-only
	STATUS current
	DESCRIPTION
		"Priority level of the member within the pool.
		Used by priority member load balancing mode."
	::= { poolMemberEntry 6 }

poolMemberWeight OBJECT-TYPE
	SYNTAX INTEGER
	MAX-ACCESS read-only
	STATUS current
	DESCRIPTION
		"Weight of the member within the pool.
		Used during dynamically calculated ratio 
		load balancing."
	::= { poolMemberEntry 7 }

poolMemberRipeness OBJECT-TYPE
	SYNTAX INTEGER
	MAX-ACCESS read-only
	STATUS current
	DESCRIPTION
		"The current load balancing state in member
		ratio load balancing mode."
	::= { poolMemberEntry 8 }

poolMemberBitsin OBJECT-TYPE
	SYNTAX 	Counter32
	MAX-ACCESS read-only
	STATUS current
	DESCRIPTION
		"The total bits in for this pool member."
	::= { poolMemberEntry 9 }

poolMemberBitsout OBJECT-TYPE
	SYNTAX 	Counter32
	MAX-ACCESS read-only
	STATUS current
	DESCRIPTION
		"The total bits out for this pool member."
	::= { poolMemberEntry 10 }

poolMemberBitsinHi32 OBJECT-TYPE
	SYNTAX 	Counter32
	MAX-ACCESS read-only
	STATUS current
	DESCRIPTION
		"The total bits in for this pool member."
	::= { poolMemberEntry 11 }

poolMemberBitsoutHi32 OBJECT-TYPE
	SYNTAX 	Counter32
	MAX-ACCESS read-only
	STATUS current
	DESCRIPTION
		"The total bits out for this pool member."
	::= { poolMemberEntry 12 }

poolMemberPktsin OBJECT-TYPE
	SYNTAX 	Counter32
	MAX-ACCESS read-only
	STATUS current
	DESCRIPTION
		"The total packets in for this pool member."
	::= { poolMemberEntry 13 }

poolMemberPktsout OBJECT-TYPE
	SYNTAX 	Counter32
	MAX-ACCESS read-only
	STATUS current
	DESCRIPTION
		"The total packets out for this pool member."
	::= { poolMemberEntry 14 }

poolMemberPktsinHi32 OBJECT-TYPE
	SYNTAX 	Counter32
	MAX-ACCESS read-only
	STATUS current
	DESCRIPTION
		"The total packets in for this pool member."
	::= { poolMemberEntry 15 }

poolMemberPktsoutHi32 OBJECT-TYPE
	SYNTAX 	Counter32
	MAX-ACCESS read-only
	STATUS current
	DESCRIPTION
		"The total packets out for this pool member."
	::= { poolMemberEntry 16 }

poolMemberConnLimit OBJECT-TYPE
	SYNTAX INTEGER (0..65535)
	MAX-ACCESS read-only
	STATUS current
	DESCRIPTION
		"The maximum number of connections this pool
		member can have open at any one time."
	::= { poolMemberEntry 17 }

poolMemberMaxConn OBJECT-TYPE
	SYNTAX INTEGER (0..65535)
	MAX-ACCESS read-only
	STATUS current
	DESCRIPTION
		"The maximum number of connections this pool
		member has had open at any one time."
	::= { poolMemberEntry 18 }

poolMemberCurrentConn OBJECT-TYPE
	SYNTAX INTEGER (0..65535)
	MAX-ACCESS read-only
	STATUS current
	DESCRIPTION
		"The current number of connections this pool
		member has open."
	::= { poolMemberEntry 19 }

poolMemberTotalConn OBJECT-TYPE
	SYNTAX Counter32
	MAX-ACCESS read-only
	STATUS current
	DESCRIPTION
		"The total number of connections this pool
		 member have served since the pool member started."
	::= { poolMemberEntry 20 }

poolMemberStatus OBJECT-TYPE
 	SYNTAX BigAPIStatus
 	MAX-ACCESS read-only
 	STATUS current
 	DESCRIPTION
 		"The status of this pool member."
 	::= { poolMemberEntry 21 }
 
poolMemberIPStatus OBJECT-TYPE
 	SYNTAX BigAPIStatus
 	MAX-ACCESS read-only
 	STATUS current
 	DESCRIPTION
 		"The status of this pool member's IP address."
 	::= { poolMemberEntry 22 }

poolMemberHCBitsin OBJECT-TYPE
	SYNTAX 	Counter64
	MAX-ACCESS read-only
	STATUS current
	DESCRIPTION
		"The total bits in for this pool member."
	::= { poolMemberEntry 23 }

poolMemberHCBitsout OBJECT-TYPE
	SYNTAX 	Counter64
	MAX-ACCESS read-only
	STATUS current
	DESCRIPTION
		"The total bits out for this pool member."
	::= { poolMemberEntry 24 }

poolMemberHCPktsin OBJECT-TYPE
	SYNTAX 	Counter64
	MAX-ACCESS read-only
	STATUS current
	DESCRIPTION
		"The total packets in for this pool member."
	::= { poolMemberEntry 25 }

poolMemberHCPktsout OBJECT-TYPE
	SYNTAX 	Counter64
	MAX-ACCESS read-only
	STATUS current
	DESCRIPTION
		"The total packets out for this pool member."
	::= { poolMemberEntry 26 }

--================================================================
-- SSL Proxy 
--================================================================

sslProxyNumber OBJECT-TYPE
	SYNTAX INTEGER (0..65535)
	MAX-ACCESS read-only
	STATUS current
	DESCRIPTION
		"The number of SSL Proxies on this BIG-IP."
	::= { sslProxy 1 }

sslProxyTable OBJECT-TYPE
	SYNTAX SEQUENCE OF SslProxyEntry
	MAX-ACCESS not-accessible
	STATUS current
	DESCRIPTION
		"A table containing information about the BIG-IP SSL Proxies."
	::= { sslProxy 2 }

sslProxyEntry OBJECT-TYPE
	SYNTAX SslProxyEntry
	MAX-ACCESS not-accessible
	STATUS current
	DESCRIPTION
		"Columns in the SSL Proxy Table."
	INDEX { sslProxyOrigIpAddress, sslProxyOrigPort, sslProxyDestIpAddress, sslProxyDestPort }
	::= { sslProxyTable 1 }

SslProxyEntry ::=
	SEQUENCE {
		sslProxyOrigIpAddress		IpAddress,
		sslProxyOrigPort		INTEGER,
		sslProxyDestIpAddress		IpAddress,
		sslProxyDestPort		INTEGER,
		sslProxyNetmask			IpAddress,
		sslProxyBroadcast		IpAddress,
		sslProxyUnitId			INTEGER,
		sslProxyEnabled			INTEGER,
		sslProxyInterfaceName		DisplayString, -- This has been deprecated.
		sslProxyLastHopPool		DisplayString,
		sslProxyVLANs			DisplayString,
		sslProxyLocalTarget		INTEGER,
		sslProxyAkamaize		INTEGER,
		sslProxyUseSSL			INTEGER,
		sslProxyBitsin			Counter32,
		sslProxyBitsout			Counter32,
		sslProxyBitsinHi32		Counter32,
		sslProxyBitsoutHi32		Counter32,
		sslProxyPktsin			Counter32,
		sslProxyPktsout			Counter32,
		sslProxyPktsinHi32		Counter32,
		sslProxyPktsoutHi32		Counter32,
		sslProxyConnLimit		INTEGER,
		sslProxyMaxConn			INTEGER,
		sslProxyCurrentConn		INTEGER,
		sslProxyTotalConn		Counter32,
		sslProxyUseServerSSL		INTEGER,
		sslProxyArpEnabled		INTEGER,
		sslProxyHTTPHeaderToAdd         DisplayString,
		sslProxyInsertClientCipher      INTEGER,
		sslProxyRewriteRedirects        INTEGER,
		sslProxyClientInvalidVersions   Counter32,
		sslProxyServerInvalidVersions   Counter32,
		sslProxyClientCertificate       INTEGER,
		sslProxyVerifyClientOnce        INTEGER,
		sslProxyVerifyClientDepth       INTEGER,
		sslProxyClientSessionCacheTimeout INTEGER,
		sslProxyClientSessionCacheSize  INTEGER,
		sslProxyChainFileName		DisplayString,
		sslProxyServerChainFileName	DisplayString,
		sslProxyCAFileFileName		DisplayString,
		sslProxyServerCAFileFileName	DisplayString,
		sslProxyCAPathFileName		DisplayString, 
		sslProxyServerCAPathFileName	DisplayString,
		sslProxyCRLFileFileName		DisplayString,
		sslProxyServerCRLFileFileName	DisplayString,
		sslProxyCRLPathFileName		DisplayString,
		sslProxyServerCRLPathFileName	DisplayString,
		sslProxyClientCertCAFileFileName	DisplayString,
		sslProxyInsertClientSessionID	INTEGER,
		sslProxyInsertClientIPAddrPort	INTEGER,
		sslProxyServerCertificate	INTEGER,
		sslProxyVerifyServerDepth	INTEGER,
		sslProxyTCPKeepAlivesEnabled	INTEGER,
		sslProxyServerTCPKeepAlivesEnabled	INTEGER,
		sslProxyHCBitsin		Counter64,
		sslProxyHCBitsout		Counter64,
		sslProxyHCPktsin		Counter64,
		sslProxyHCPktsout		Counter64
	}

sslProxyOrigIpAddress OBJECT-TYPE
	SYNTAX IpAddress
	MAX-ACCESS read-only
	STATUS current
	DESCRIPTION
		"The original IP address of this SSL proxy."
	::= { sslProxyEntry 1 }

sslProxyOrigPort OBJECT-TYPE
	SYNTAX INTEGER (0..65535)
	MAX-ACCESS read-only
	STATUS current
	DESCRIPTION
		"The original port of this SSL proxy."
	::= { sslProxyEntry 2 }

sslProxyDestIpAddress OBJECT-TYPE
	SYNTAX IpAddress
	MAX-ACCESS read-only
	STATUS current
	DESCRIPTION
		"The destination IP address of this SSL proxy."
	::= { sslProxyEntry 3 }

sslProxyDestPort OBJECT-TYPE
	SYNTAX INTEGER (0..65535)
	MAX-ACCESS read-only
	STATUS current
	DESCRIPTION
		"The destination port of this SSL proxy."
	::= { sslProxyEntry 4 }

sslProxyNetmask OBJECT-TYPE
	SYNTAX IpAddress
	MAX-ACCESS read-only
	STATUS current
	DESCRIPTION
		"The netmask of this SSL proxy."
	::= { sslProxyEntry 5 }

sslProxyBroadcast OBJECT-TYPE
	SYNTAX IpAddress
	MAX-ACCESS read-only
	STATUS current
	DESCRIPTION
		"The broadcast address of this SSL proxy."
	::= { sslProxyEntry 6 }

sslProxyUnitId OBJECT-TYPE
	SYNTAX INTEGER (0..65535)
	MAX-ACCESS read-only
	STATUS current
	DESCRIPTION
		"The unit id of this SSL proxy."
	::= { sslProxyEntry 7 }

sslProxyEnabled OBJECT-TYPE
	SYNTAX INTEGER  { true(1), false(2) }
	MAX-ACCESS read-only
	STATUS current
	DESCRIPTION
		"States whether this SSL proxy is enabled; 
		true = enabled, false = not enabled."
	::= { sslProxyEntry 8 }

sslProxyInterfaceName OBJECT-TYPE
	SYNTAX DisplayString (SIZE (0..255))
	MAX-ACCESS read-only
	STATUS deprecated
	DESCRIPTION
		"SSL proxies now exist on VLANS and not specific interfaces. 
		This OID is deprecated and will always return 0.0.0.0."
	::= { sslProxyEntry 9 }

sslProxyLastHopPool OBJECT-TYPE
	SYNTAX DisplayString (SIZE (0..255))
	MAX-ACCESS read-only
	STATUS current
	DESCRIPTION
		"The name of the last hop pool for this SSL proxy."
	::= { sslProxyEntry 10 }

sslProxyVLANs OBJECT-TYPE
	SYNTAX 	DisplayString (SIZE (0..255))
	MAX-ACCESS read-only
	STATUS current
	DESCRIPTION
		"If this list is empty, (the default) this SSL proxy will 
		be accessible on all VLANS.  If this list is not empty, 
		this SSL proxy will be accessible only on those VLANs
		specified in the list."
	::= { sslProxyEntry 11 }

sslProxyLocalTarget OBJECT-TYPE
	SYNTAX INTEGER  { true(1), false(2) }
	MAX-ACCESS read-only
	STATUS current
	DESCRIPTION
		"Local target of SSL proxy, virtual server or node server
		true if the target is a node, false if the target is a virtual
		server."
	::= { sslProxyEntry 12 }

sslProxyAkamaize OBJECT-TYPE
	SYNTAX INTEGER  { true(1), false(2) }
	MAX-ACCESS read-only
	STATUS current
	DESCRIPTION
		"States whether Akamaize feature is enabled;
		true = enabled, false = disabled."
	::= { sslProxyEntry 13 }

sslProxyUseSSL OBJECT-TYPE
	SYNTAX INTEGER  { true(1), false(2) }
	MAX-ACCESS read-only
	STATUS current
	DESCRIPTION
		"States whether the SSL proxy will use SSL;
		true = SSL, false = no SSL."
	::= { sslProxyEntry 14 }

sslProxyBitsin OBJECT-TYPE
	SYNTAX 	Counter32
	MAX-ACCESS read-only
	STATUS current
	DESCRIPTION
		"The total bits in for this SSL proxy."
	::= { sslProxyEntry 15 }

sslProxyBitsout OBJECT-TYPE
	SYNTAX 	Counter32
	MAX-ACCESS read-only
	STATUS current
	DESCRIPTION
		"The total bits out for this SSL proxy."
	::= { sslProxyEntry 16 }

sslProxyBitsinHi32 OBJECT-TYPE
	SYNTAX 	Counter32
	MAX-ACCESS read-only
	STATUS current
	DESCRIPTION
		"The total bits in for this SSL proxy."
	::= { sslProxyEntry 17 }

sslProxyBitsoutHi32 OBJECT-TYPE
	SYNTAX 	Counter32
	MAX-ACCESS read-only
	STATUS current
	DESCRIPTION
		"The total bits out for this SSL proxy."
	::= { sslProxyEntry 18 }

sslProxyPktsin OBJECT-TYPE
	SYNTAX 	Counter32
	MAX-ACCESS read-only
	STATUS current
	DESCRIPTION
		"The total packets in for this SSL proxy."
	::= { sslProxyEntry 19 }

sslProxyPktsout OBJECT-TYPE
	SYNTAX 	Counter32
	MAX-ACCESS read-only
	STATUS current
	DESCRIPTION
		"The total packets out for this SSL proxy."
	::= { sslProxyEntry 20 }

sslProxyPktsinHi32 OBJECT-TYPE
	SYNTAX 	Counter32
	MAX-ACCESS read-only
	STATUS current
	DESCRIPTION
		"The total packets in for this SSL proxy."
	::= { sslProxyEntry 21 }

sslProxyPktsoutHi32 OBJECT-TYPE
	SYNTAX 	Counter32
	MAX-ACCESS read-only
	STATUS current
	DESCRIPTION
		"The total packets out for this SSL proxy."
	::= { sslProxyEntry 22 }

sslProxyConnLimit OBJECT-TYPE
	SYNTAX INTEGER (0..65535)
	MAX-ACCESS read-only
	STATUS current
	DESCRIPTION
		"The maximum number of connections this SSL proxy
		can have open at any one time."
	::= { sslProxyEntry 23 }

sslProxyMaxConn OBJECT-TYPE
	SYNTAX INTEGER (0..65535)
	MAX-ACCESS read-only
	STATUS current
	DESCRIPTION
		"The maximum number of connections this SSL proxy
		member has had open at any one time."
	::= { sslProxyEntry 24 }

sslProxyCurrentConn OBJECT-TYPE
	SYNTAX INTEGER (0..65535)
	MAX-ACCESS read-only
	STATUS current
	DESCRIPTION
		"The current number of connections this SSL proxy has open."
	::= { sslProxyEntry 25 }

sslProxyTotalConn OBJECT-TYPE
	SYNTAX Counter32
	MAX-ACCESS read-only
	STATUS current
	DESCRIPTION
		"The total number of connections this SSL proxy
		 has served since the SSL proxy started."
	::= { sslProxyEntry 26 }

sslProxyUseServerSSL OBJECT-TYPE
	SYNTAX INTEGER { true(1), false(2)}
	MAX-ACCESS read-only
	STATUS current
	DESCRIPTION
		"States whether this SSL proxy will use server-side SSL;
		true = server-side SSL, false = no server-side SSL."
	::= { sslProxyEntry 27 }

sslProxyArpEnabled OBJECT-TYPE
	SYNTAX INTEGER { true(1), false(2)}
	MAX-ACCESS read-only
	STATUS current
	DESCRIPTION
		"States whether ARP will be enabled for this SSL proxy;
		true = ARP enabled, false = ARP disabled."
	::= { sslProxyEntry 28 }

sslProxyHTTPHeaderToAdd OBJECT-TYPE
	SYNTAX DisplayString (SIZE (0..255))
	MAX-ACCESS read-only
	STATUS current
	DESCRIPTION
		"Text to be added to an HTTP packet header."
	::= { sslProxyEntry 29 }

sslProxyInsertClientCipher OBJECT-TYPE
	SYNTAX INTEGER { true(1), false(2)}
	MAX-ACCESS read-only
	STATUS current
	DESCRIPTION
		"States whether the negotiated client request SSL 
		ciphersuite will be inserted into the HTTP packet header;
		true = yes, false = no."
	::= { sslProxyEntry 30 }

sslProxyRewriteRedirects OBJECT-TYPE
	SYNTAX INTEGER 
	MAX-ACCESS read-only
	STATUS current
	DESCRIPTION
                "The number of rewrite redirects specified for this SSL proxy."
	::= { sslProxyEntry 31 }

sslProxyClientInvalidVersions OBJECT-TYPE
	SYNTAX Counter32
	MAX-ACCESS read-only
	STATUS current
	DESCRIPTION
                "The total number of client invalid versions for this SSL proxy."
	::= { sslProxyEntry 32 }

sslProxyServerInvalidVersions OBJECT-TYPE
	SYNTAX Counter32
	MAX-ACCESS read-only
	STATUS current
	DESCRIPTION
                "The total number of server invalid versions for this SSL proxy."
	::= { sslProxyEntry 33 }

sslProxyClientCertificate OBJECT-TYPE
    SYNTAX INTEGER { 
        clientCertificateIgnored( 1 ),
        clientCertificateRequested( 2 ),
        clientCertificateRequired( 3 )
    }
	MAX-ACCESS read-only
	STATUS current
	DESCRIPTION
                "Flag describing the use of the client certificate."
	::= { sslProxyEntry 34 }

sslProxyVerifyClientOnce OBJECT-TYPE
	SYNTAX INTEGER {true(1), false(2)}
	MAX-ACCESS read-only
	STATUS current
	DESCRIPTION
                "States whether each client will be verified one time 
		by this SSL proxy; true = verify once, false = verify each time."
	::= { sslProxyEntry 35 }

sslProxyVerifyClientDepth OBJECT-TYPE
	SYNTAX INTEGER {true(1), false(2)}
	MAX-ACCESS read-only
	STATUS current
	DESCRIPTION
                "States whether this SSL proxy will verify client depth;
		true = verify, false = do not verify."
	::= { sslProxyEntry 36 }

sslProxyClientSessionCacheTimeout OBJECT-TYPE
	SYNTAX INTEGER
	MAX-ACCESS read-only
	STATUS current
	DESCRIPTION
                "The timeout value for the client session cache for this 
		SSL proxy in seconds."
	::= { sslProxyEntry 37 }

sslProxyClientSessionCacheSize OBJECT-TYPE
	SYNTAX INTEGER
	MAX-ACCESS read-only
	STATUS current
	DESCRIPTION
                "The size of the cache for each client session for this 
		SSL proxy."
	::= { sslProxyEntry 38 }

sslProxyChainFileName OBJECT-TYPE
	SYNTAX DisplayString (SIZE (0..1024))
	MAX-ACCESS read-only
	STATUS current
	DESCRIPTION
		""
	::= { sslProxyEntry 39 }

sslProxyServerChainFileName OBJECT-TYPE
	SYNTAX DisplayString (SIZE (0..1024))
	MAX-ACCESS read-only
	STATUS current
	DESCRIPTION
        	""
	::= { sslProxyEntry 40 }


sslProxyCAFileFileName OBJECT-TYPE
	SYNTAX DisplayString (SIZE (0..1024))
	MAX-ACCESS read-only
	STATUS current
	DESCRIPTION
                ""
	::= { sslProxyEntry 41 }

sslProxyServerCAFileFileName OBJECT-TYPE
	SYNTAX 	DisplayString (SIZE (0..1024))
	MAX-ACCESS read-only
	STATUS current
	DESCRIPTION
                ""
	::= { sslProxyEntry 42 }

sslProxyCAPathFileName OBJECT-TYPE
	SYNTAX DisplayString (SIZE (0..1024))
	MAX-ACCESS read-only
	STATUS current
	DESCRIPTION
                ""
	::= { sslProxyEntry 43 }

sslProxyServerCAPathFileName OBJECT-TYPE
	SYNTAX 	DisplayString (SIZE (0..1024))
	MAX-ACCESS read-only
	STATUS current
	DESCRIPTION
                ""
	::= { sslProxyEntry 44 }

sslProxyCRLFileFileName OBJECT-TYPE
	SYNTAX DisplayString (SIZE (0..1024))
	MAX-ACCESS read-only
	STATUS current
	DESCRIPTION
                ""
	::= { sslProxyEntry 45 }

sslProxyServerCRLFileFileName OBJECT-TYPE
	SYNTAX DisplayString (SIZE (0..1024))
	MAX-ACCESS read-only
	STATUS current
	DESCRIPTION
                ""
	::= { sslProxyEntry 46 }

sslProxyCRLPathFileName OBJECT-TYPE
	SYNTAX DisplayString (SIZE (0..1024))
	MAX-ACCESS read-only
	STATUS current
	DESCRIPTION
                ""
	::= { sslProxyEntry 47 }

sslProxyServerCRLPathFileName OBJECT-TYPE
	SYNTAX DisplayString (SIZE (0..1024))
	MAX-ACCESS read-only
	STATUS current
	DESCRIPTION
                ""
	::= { sslProxyEntry 48 }

sslProxyClientCertCAFileFileName OBJECT-TYPE
	SYNTAX DisplayString (SIZE (0..1024))
	MAX-ACCESS read-only
	STATUS current
	DESCRIPTION
                ""
	::= { sslProxyEntry 49 }

sslProxyInsertClientSessionID OBJECT-TYPE
	SYNTAX INTEGER
	MAX-ACCESS read-only
	STATUS current
	DESCRIPTION
		"Bitmask specifying which SSL session ID(s) to include in the HTTP header."
	::= { sslProxyEntry 50 }

sslProxyInsertClientIPAddrPort OBJECT-TYPE
	SYNTAX INTEGER
	MAX-ACCESS read-only
	STATUS current
	DESCRIPTION
		""
	::= { sslProxyEntry 51 }

sslProxyServerCertificate OBJECT-TYPE
	SYNTAX INTEGER {
		serverCertificateIgnored(1),
		serverCertificateRequired(3)
	}
	MAX-ACCESS read-only
	STATUS current
	DESCRIPTION
		""
	::= { sslProxyEntry 52 }

sslProxyVerifyServerDepth OBJECT-TYPE
	SYNTAX INTEGER
	MAX-ACCESS read-only
	STATUS current
	DESCRIPTION
                ""
	::= { sslProxyEntry 53 }

sslProxyTCPKeepAlivesEnabled OBJECT-TYPE
	SYNTAX INTEGER { true(1), false(2) }
	MAX-ACCESS read-only
	STATUS current
	DESCRIPTION
                ""
	::= { sslProxyEntry 54 }

sslProxyServerTCPKeepAlivesEnabled OBJECT-TYPE
	SYNTAX INTEGER { true(1), false(2) }
	MAX-ACCESS read-only
	STATUS current
	DESCRIPTION
                ""
	::= { sslProxyEntry 55 }

sslProxyHCBitsin OBJECT-TYPE
	SYNTAX 	Counter64
	MAX-ACCESS read-only
	STATUS current
	DESCRIPTION
		"The total bits in for this SSL proxy."
	::= { sslProxyEntry 56 }

sslProxyHCBitsout OBJECT-TYPE
	SYNTAX 	Counter64
	MAX-ACCESS read-only
	STATUS current
	DESCRIPTION
		"The total bits out for this SSL proxy."
	::= { sslProxyEntry 57 }

sslProxyHCPktsin OBJECT-TYPE
	SYNTAX 	Counter64
	MAX-ACCESS read-only
	STATUS current
	DESCRIPTION
		"The total packets in for this SSL proxy."
	::= { sslProxyEntry 58 }

sslProxyHCPktsout OBJECT-TYPE
	SYNTAX 	Counter64
	MAX-ACCESS read-only
	STATUS current
	DESCRIPTION
		"The total packets out for this SSL proxy."
	::= { sslProxyEntry 59 }

	
--================================================================
-- VLANs
--================================================================

vlanNumber OBJECT-TYPE
	SYNTAX INTEGER (0..65535)
	MAX-ACCESS read-only
	STATUS current
	DESCRIPTION
		"The number of VLANs on this system."
	::= { vlan 1 }

vlanTable OBJECT-TYPE
	SYNTAX SEQUENCE OF VlanEntry
	MAX-ACCESS not-accessible
	STATUS current
	DESCRIPTION
		"A table containing information for VLANs."
	::= { vlan 2 }

vlanEntry OBJECT-TYPE
	SYNTAX VlanEntry
	MAX-ACCESS not-accessible
	STATUS current
	DESCRIPTION
		"Columns in the VLAN Table."
	INDEX { vlanName }
	::= { vlanTable 1 }

VlanEntry ::=
	SEQUENCE {
		vlanName			DisplayString,
		vlanID				INTEGER,
		vlanTag				INTEGER,
		vlanAllowOtherProxyARP		INTEGER,
		vlanPortLockedDown		INTEGER,
		vlanTaggedPorts			DisplayString,
		vlanUntaggedPorts		DisplayString,
		vlanSnatAutomap			INTEGER,
		vlanArmed			INTEGER,
		vlanTimeout			INTEGER,
		vlanMirrorVLANPortNames		DisplayString,
		vlanMirrorHashMode		INTEGER,
		vlanMirrorHashPort		INTEGER
	}

vlanName OBJECT-TYPE
	SYNTAX DisplayString (SIZE (0..255))
	MAX-ACCESS read-only
	STATUS current
	DESCRIPTION
		"The name of this VLAN."
	::= { vlanEntry 1 }

vlanID OBJECT-TYPE
	SYNTAX INTEGER
	MAX-ACCESS read-only
	STATUS current
	DESCRIPTION
		"Numeric ID for this VLAN."
	::= { vlanEntry 2 }

vlanTag OBJECT-TYPE
	SYNTAX INTEGER
	MAX-ACCESS read-only
	STATUS current
	DESCRIPTION
		"Numeric tag for this VLAN."
	::= { vlanEntry 3 }

vlanAllowOtherProxyARP OBJECT-TYPE
	SYNTAX INTEGER { true(1), false(2) }
	MAX-ACCESS read-only
	STATUS current
	DESCRIPTION
		"States whether other VLANS are allowed to perform 
		proxy ARP requests for this VLAN; true = allowed, 
		false = not allowed."
	::= { vlanEntry 4 }

vlanPortLockedDown OBJECT-TYPE
	SYNTAX INTEGER { true(1), false(2) }
	MAX-ACCESS read-only
	STATUS current
	DESCRIPTION
		"States whether the port lock down feature is 
		enabled for this VLAN; true = enabled, false = disabled."
	::= { vlanEntry 5 }

vlanTaggedPorts OBJECT-TYPE
	SYNTAX DisplayString (SIZE (0..255))
	MAX-ACCESS read-only
	STATUS current
	DESCRIPTION
		"A list of the tagged ports on this VLAN."
	::= { vlanEntry 6 }

vlanUntaggedPorts OBJECT-TYPE
	SYNTAX DisplayString (SIZE (0..255))
	MAX-ACCESS read-only
	STATUS current
	DESCRIPTION
		"A list of the untagged ports on this VLAN."
	::= { vlanEntry 7 }

vlanSnatAutomap OBJECT-TYPE
	SYNTAX INTEGER { true(1), false(2) }
	MAX-ACCESS read-only
	STATUS current
	DESCRIPTION
		"States whether the SNAT automap feature is enabled 
		for this VLAN; true = enabled, false = disabled."
	::= { vlanEntry 8 }

vlanArmed OBJECT-TYPE
	SYNTAX INTEGER { true(1), false(2) }
	MAX-ACCESS read-only
	STATUS current
	DESCRIPTION
		"States whether this vlan is armed; true = armed,
		false = disarmed."
	::= { vlanEntry 9 }

vlanTimeout OBJECT-TYPE
	SYNTAX INTEGER
	MAX-ACCESS read-only
	STATUS current
	DESCRIPTION
		"The timeout value for this VLAN, in seconds."
	::= { vlanEntry 10 }

vlanMirrorVLANPortNames OBJECT-TYPE
	SYNTAX DisplayString (SIZE (0..255))
	MAX-ACCESS read-only
	STATUS current
	DESCRIPTION
		""
	::= { vlanEntry 11 }

vlanMirrorHashMode OBJECT-TYPE
	SYNTAX INTEGER { true(1), false(2) }
	MAX-ACCESS read-only
	STATUS current
	DESCRIPTION
		""
	::= { vlanEntry 12 }

vlanMirrorHashPort OBJECT-TYPE
	SYNTAX INTEGER { true(1), false(2) }
	MAX-ACCESS read-only
	STATUS current
	DESCRIPTION
		""
	::= { vlanEntry 13 }



--================================================================
-- selfIP Table 
--================================================================

selfIPNumber OBJECT-TYPE
	SYNTAX INTEGER (0..65535)
	MAX-ACCESS read-only
	STATUS current
	DESCRIPTION
		"The number of self IPs on this system."
	::= { selfIP 1 }

selfIPTable OBJECT-TYPE
	SYNTAX SEQUENCE OF SelfIPEntry
	MAX-ACCESS not-accessible
	STATUS current
	DESCRIPTION
		"A table containing information for self IPs."
	::= { selfIP 2 }

selfIPEntry OBJECT-TYPE
	SYNTAX SelfIPEntry
	MAX-ACCESS not-accessible
	STATUS current
	DESCRIPTION
		"Columns in the selfIP Table."
	INDEX { selfIPAddress }
	::= { selfIPTable 1 }

SelfIPEntry ::=
	SEQUENCE {
		selfIPAddress			IpAddress,
		selfIPNetmask			IpAddress,
		selfIPBroadcast			IpAddress,
		selfIPUnitID			INTEGER,
		selfIPVLAN			DisplayString,
		selfIPSnatAutomap		INTEGER,
		selfIPIsFloating		INTEGER
	}

selfIPAddress OBJECT-TYPE
	SYNTAX IpAddress
	MAX-ACCESS read-only
	STATUS current
	DESCRIPTION
		"The IP of this self IP address."
	::= { selfIPEntry 1 }

selfIPNetmask OBJECT-TYPE
	SYNTAX IpAddress
	MAX-ACCESS read-only
	STATUS current
	DESCRIPTION
		"The netmask for this self IP address."
	::= { selfIPEntry 2 }

selfIPBroadcast OBJECT-TYPE
	SYNTAX IpAddress
	MAX-ACCESS read-only
	STATUS current
	DESCRIPTION
		"The broadcast address for this self IP address."
	::= { selfIPEntry 3 }

selfIPUnitID OBJECT-TYPE
	SYNTAX INTEGER
	MAX-ACCESS read-only
	STATUS current
	DESCRIPTION
		"For redundant systems, unit number associated with the self 
		IP address."
	::= { selfIPEntry 4 }

selfIPVLAN OBJECT-TYPE
	SYNTAX DisplayString (SIZE (0..255))
	MAX-ACCESS read-only
	STATUS current
	DESCRIPTION
		"The VLAN associated with this self IP address."
	::= { selfIPEntry 5 }

selfIPSnatAutomap OBJECT-TYPE
	SYNTAX INTEGER {
		true(1),
		false(2)
	}
	MAX-ACCESS read-only
	STATUS current
	DESCRIPTION
		"SNAT auto map feature for self IP addresses;
		true = auto map enabled."
	::= { selfIPEntry 6 }

selfIPIsFloating OBJECT-TYPE
	SYNTAX INTEGER {
		true(1),
		false(2)
	}
	MAX-ACCESS read-only
	STATUS current
	DESCRIPTION
		"States whether self IP address is shared;
		true = shared, false = not shared."
	::= { selfIPEntry 7 }

--================================================================
-- trunk Table 
--================================================================

trunkNumber OBJECT-TYPE
	SYNTAX INTEGER (0..65535)
	MAX-ACCESS read-only
	STATUS current
	DESCRIPTION
		"The number of trunks on this system."
	::= { trunk 1 }

trunkTable OBJECT-TYPE
	SYNTAX SEQUENCE OF TrunkEntry
	MAX-ACCESS not-accessible
	STATUS current
	DESCRIPTION
		"A table containing information for trunks."
	::= { trunk 2 }

trunkEntry OBJECT-TYPE
	SYNTAX TrunkEntry
	MAX-ACCESS not-accessible
	STATUS current
	DESCRIPTION
		"Columns in the trunk Table."
	INDEX { trunkControllingInterface }
	::= { trunkTable 1 }

TrunkEntry ::=
	SEQUENCE {
		trunkControllingInterface	DisplayString,
		trunkInterfaces			DisplayString,
		trunkMediaSpeed			Counter64
	}

trunkControllingInterface OBJECT-TYPE
	SYNTAX DisplayString (SIZE (0..255))
	MAX-ACCESS read-only
	STATUS current
	DESCRIPTION
		"The name of the controlling interface for this interface trunk."
	::= { trunkEntry 1 }

trunkInterfaces OBJECT-TYPE
	SYNTAX DisplayString (SIZE (0..255))
	MAX-ACCESS read-only
	STATUS current
	DESCRIPTION
		"A list of the interfaces on this interface trunk."
	::= { trunkEntry 2 }

trunkMediaSpeed OBJECT-TYPE
	SYNTAX 	Counter64
	MAX-ACCESS	read-only
	STATUS	current
	DESCRIPTION
		"Aggregate trunk media speed in bits/s."
	::= { trunkEntry 3 }

--================================================================
-- Virtual Addresses
--================================================================

virtualAddressNumber OBJECT-TYPE
	SYNTAX INTEGER (0..65535)
	MAX-ACCESS read-only
	STATUS current
	DESCRIPTION
		"The number of virtual addresses on this BIG-IP."
	::= { virtualAddress 1 }

virtualAddressTable OBJECT-TYPE
	SYNTAX SEQUENCE OF VirtualAddressEntry
	MAX-ACCESS not-accessible
	STATUS current
	DESCRIPTION
		"A table containing information about the BIG-IP
		Virtual Server addresses."
	::= { virtualAddress 2 }

virtualAddressEntry OBJECT-TYPE
	SYNTAX VirtualAddressEntry
	MAX-ACCESS not-accessible
	STATUS current
	DESCRIPTION
		"Columns in the Virtual Address Table."
	INDEX { virtualAddressIpAddress }
	::= { virtualAddressTable 1 }

VirtualAddressEntry ::=
	SEQUENCE {
		virtualAddressIpAddress		IpAddress,
		virtualAddressStatus		INTEGER,
		virtualAddressConnLimit		INTEGER,
		virtualAddressNetmask		IpAddress,
		virtualAddressBroadcast		IpAddress,
		virtualAddressInterface		DisplayString, -- This has been deprecated
		virtualAddressFailoverFlags	INTEGER, -- This flag has been deprecated
		virtualAddressOctetsIn		Counter32,
		virtualAddressOctetsOut		Counter32,
		virtualAddressPacketsIn		Counter32,
		virtualAddressPacketsOut	Counter32,
		virtualAddressCurrentConn	INTEGER,
		virtualAddressMaxConn		INTEGER,
		virtualAddressTotalConn		Counter32,
		virtualAddressOctetsInHi32	Counter32,
		virtualAddressOctetsOutHi32	Counter32,
		virtualAddressPacketsInHi32	Counter32,
		virtualAddressPacketsOutHi32	Counter32,
		virtualAddressUnitId		INTEGER,
		virtualAddressHCOctetsIn	Counter64,
		virtualAddressHCOctetsOut	Counter64,
		virtualAddressHCPacketsIn	Counter64,
		virtualAddressHCPacketsOut	Counter64
	}

virtualAddressIpAddress OBJECT-TYPE
	SYNTAX IpAddress
	MAX-ACCESS read-only
	STATUS current
	DESCRIPTION
		"The IP address for this virtual server."
	::= { virtualAddressEntry 1 }

virtualAddressStatus OBJECT-TYPE
	SYNTAX INTEGER {
		disabled(1),
		enabled(2)
	}
	MAX-ACCESS read-only
	STATUS current
	DESCRIPTION
		"Is this server in maintenance mode?"
	::= { virtualAddressEntry 2 }

virtualAddressConnLimit OBJECT-TYPE
	SYNTAX INTEGER (0..65535)
	MAX-ACCESS read-only
	STATUS current
	DESCRIPTION
		"The total number of connections this virtual address
		can support at one time."
	::= { virtualAddressEntry 3 }

virtualAddressNetmask OBJECT-TYPE
	SYNTAX IpAddress
	MAX-ACCESS read-only
	STATUS current
	DESCRIPTION
		"The netmask for this virtual address."
	::= { virtualAddressEntry 4 }

virtualAddressBroadcast OBJECT-TYPE
	SYNTAX IpAddress
	MAX-ACCESS read-only
	STATUS current
	DESCRIPTION
		"The broadcast address for this virtual address."
	::= { virtualAddressEntry 5 }

virtualAddressInterface OBJECT-TYPE
	SYNTAX DisplayString (SIZE (0..8))
	MAX-ACCESS read-only
	STATUS deprecated
	DESCRIPTION
		"This has been deprecated. virtualAddresses are no longer 
		associated a specific interface. Instead each virtualServer 
		of a virtualAddress is associated with a VLAN. A query will 
		now always return none."
	::= { virtualAddressEntry 6 }

virtualAddressFailoverFlags OBJECT-TYPE
	SYNTAX INTEGER {
		mirrorconnections(1),
		mirrorpersistence(2),
		mirrorconnectionspersistence(3)
	}
	MAX-ACCESS read-only
	STATUS current
	DESCRIPTION
		"The fail-over flags for the this virtual address.
		The virtualAddressFailoverFlag is no longer relevant. Mirroring
		is controlled through the virtualServerFailoverFlag."
	::= { virtualAddressEntry 7 }

virtualAddressOctetsIn OBJECT-TYPE
	SYNTAX Counter32
	MAX-ACCESS read-only
	STATUS current
	DESCRIPTION
		"The number of octets received from the network from
		this virtual server."
	::= { virtualAddressEntry 8 }

virtualAddressOctetsOut OBJECT-TYPE
	SYNTAX Counter32
	MAX-ACCESS read-only
	STATUS current
	DESCRIPTION
		"The number of octets sent to the network from this
		virtual server."
	::= { virtualAddressEntry 9 }

virtualAddressPacketsIn OBJECT-TYPE
	SYNTAX Counter32
	MAX-ACCESS read-only
	STATUS current
	DESCRIPTION
		"The number of packets received from the network from
		this virtual server."
	::= { virtualAddressEntry 10 }

virtualAddressPacketsOut OBJECT-TYPE
	SYNTAX Counter32
	MAX-ACCESS read-only
	STATUS current
	DESCRIPTION
		"The number of packets sent to the network from this
		virtual	server."
	::= { virtualAddressEntry 11 }

virtualAddressCurrentConn OBJECT-TYPE
	SYNTAX INTEGER (0..65535)
	MAX-ACCESS read-only
	STATUS current
	DESCRIPTION
		"The number of connections currently open on this
		virtual server."
	::= { virtualAddressEntry 12 }

virtualAddressMaxConn OBJECT-TYPE
	SYNTAX INTEGER (0..65535)
	MAX-ACCESS read-only
	STATUS current
	DESCRIPTION
		"The maximum number of connections this virtual server
		has had open at any one time."
	::= { virtualAddressEntry 13 }

virtualAddressTotalConn OBJECT-TYPE
	SYNTAX Counter32
	MAX-ACCESS read-only
	STATUS current
	DESCRIPTION
		"The total number of connections this virtual server
		has served since the server started."
	::= { virtualAddressEntry 14 }

virtualAddressOctetsInHi32 OBJECT-TYPE
	SYNTAX Counter32
	MAX-ACCESS read-only
	STATUS current
	DESCRIPTION
		"The number of octets received from the network from
		this virtual server."
	::= { virtualAddressEntry 15 }

virtualAddressOctetsOutHi32 OBJECT-TYPE
	SYNTAX Counter32
	MAX-ACCESS read-only
	STATUS current
	DESCRIPTION
		"The number of octets sent to the network from this
		virtual server."
	::= { virtualAddressEntry 16 }

virtualAddressPacketsInHi32 OBJECT-TYPE
	SYNTAX Counter32
	MAX-ACCESS read-only
	STATUS current
	DESCRIPTION
		"The number of packets received from the network from
		this virtual server."
	::= { virtualAddressEntry 17 }

virtualAddressPacketsOutHi32 OBJECT-TYPE
	SYNTAX Counter32
	MAX-ACCESS read-only
	STATUS current
	DESCRIPTION
		"The number of packets sent to the network from this
		virtual	server."
	::= { virtualAddressEntry 18 }

virtualAddressUnitId OBJECT-TYPE
	SYNTAX INTEGER
	MAX-ACCESS read-only
	STATUS current
	DESCRIPTION
		"The unit id of this virtual server."
	::= { virtualAddressEntry 19 }

virtualAddressHCOctetsIn OBJECT-TYPE
	SYNTAX Counter64
	MAX-ACCESS read-only
	STATUS current
	DESCRIPTION
		"The number of octets received from the network from
		this virtual server."
	::= { virtualAddressEntry 20 }

virtualAddressHCOctetsOut OBJECT-TYPE
	SYNTAX Counter64
	MAX-ACCESS read-only
	STATUS current
	DESCRIPTION
		"The number of octets sent to the network from this
		virtual server."
	::= { virtualAddressEntry 21 }

virtualAddressHCPacketsIn OBJECT-TYPE
	SYNTAX Counter64
	MAX-ACCESS read-only
	STATUS current
	DESCRIPTION
		"The number of packets received from the network from
		this virtual server."
	::= { virtualAddressEntry 22 }

virtualAddressHCPacketsOut OBJECT-TYPE
	SYNTAX Counter64
	MAX-ACCESS read-only
	STATUS current
	DESCRIPTION
		"The number of packets sent to the network from this
		virtual	server."
	::= { virtualAddressEntry 23 }


--================================================================
--Virtual Servers
--================================================================

virtualServerNumber OBJECT-TYPE
	SYNTAX INTEGER (0..65535)
	MAX-ACCESS read-only
	STATUS current
	DESCRIPTION
		"The number of virtual servers on this BIG-IP."
	::= { virtualServer 1 }

virtualServerTable OBJECT-TYPE
	SYNTAX SEQUENCE OF VirtualServerEntry
	MAX-ACCESS not-accessible
	STATUS current
	DESCRIPTION
		"A table containing BIG-IP Virtual server information."
	::= { virtualServer 2 }

virtualServerEntry OBJECT-TYPE
	SYNTAX VirtualServerEntry
	MAX-ACCESS not-accessible
	STATUS current
	DESCRIPTION
		"Columns in the Virtual Server table."
	INDEX { virtualServerIpAddress,virtualServerPort }
	::= { virtualServerTable 1 }

VirtualServerEntry ::=
	SEQUENCE {
		virtualServerIpAddress		IpAddress,
		virtualServerPort		INTEGER,
		virtualServerStatus		INTEGER,
		virtualServerConnLimit		INTEGER,
		virtualServerAppProtocol	INTEGER, -- This has been deprecated.
		virtualServerAppProtocolTimeout INTEGER, -- This has been deprecated.
		virtualServerAppProtocolReaper	INTEGER,-- This has been deprecated.
		virtualServerPersistTimeout	INTEGER,
		virtualServerPersistMask	IpAddress,
		virtualServerSticky		INTEGER,
		virtualServerStickyMask		IpAddress,
		virtualServerFailoverFlags	INTEGER,
		virtualServerOctetsIn		Counter32,
		virtualServerOctetsOut		Counter32,
		virtualServerPacketsIn		Counter32,
		virtualServerPacketsOut		Counter32,
		virtualServerCurrentConn	INTEGER,
		virtualServerMaxConn		INTEGER,
		virtualServerTotalConn		Counter32,
		virtualServerSslNew		Counter32,
		virtualServerSslHits		Counter32,
		virtualServerSslTimeouts	Counter32,
		virtualServerSslMisses		Counter32,
		virtualServerOctetsInHi32  	Counter32,
		virtualServerOctetsOutHi32	Counter32,
		virtualServerPacketsInHi32	Counter32,
		virtualServerPacketsOutHi32	Counter32,
		virtualServerCookieMethod	INTEGER,
		virtualServerRule		DisplayString,
		virtualServerPool		DisplayString,
		virtualServerARPEnabled		INTEGER,
		virtualServerLastHopPool	DisplayString,
		virtualServerTranslateAddress	INTEGER,
		virtualServerTranslatePort	INTEGER,
		virtualServerSvcDownReset	INTEGER,
		virtualServerMayUseProxy	INTEGER,
		virtualServerAccelerate		INTEGER,
		virtualServerHCOctetsIn		Counter64,
		virtualServerHCOctetsOut	Counter64,
		virtualServerHCPacketsIn	Counter64,
		virtualServerHCPacketsOut	Counter64
	}

virtualServerIpAddress OBJECT-TYPE
	SYNTAX IpAddress
	MAX-ACCESS read-only
	STATUS current
	DESCRIPTION
		"The IP address for this virtual server.  
		Wildcard virtual servers will have an IP 
		address of 255.255.255.255"
	::= { virtualServerEntry 1}

virtualServerPort OBJECT-TYPE
	SYNTAX INTEGER (0..65535)
	MAX-ACCESS read-only
	STATUS current
	DESCRIPTION
		"The port for this virtual server."
	::= { virtualServerEntry 2 }

virtualServerStatus OBJECT-TYPE
	SYNTAX INTEGER {
		disabled(1),
		enabled(2),
		noNodeAvailable(3),
		notOnThisUnit(4)
	}
	MAX-ACCESS read-only
	STATUS current
	DESCRIPTION
		"Is this server in maintenance mode?"
	::= { virtualServerEntry 3 }

virtualServerConnLimit OBJECT-TYPE
	SYNTAX INTEGER (0..65535)
	MAX-ACCESS read-only
	STATUS current
	DESCRIPTION
		"The total number of connections this virtual server can
		support at one time."
	::= { virtualServerEntry 4 }

virtualServerAppProtocol OBJECT-TYPE
	SYNTAX INTEGER {
		none (1),
		ssl (2),
		cookie(3)
	}
	MAX-ACCESS read-only
	STATUS deprecated
	DESCRIPTION
		"This variable has been deprecated. 
		A query will always return -1.
		The application tunneling protocol this virtual server uses."
	::= { virtualServerEntry 5 }

virtualServerAppProtocolTimeout OBJECT-TYPE
	SYNTAX INTEGER (0..65535)
	MAX-ACCESS read-only
	STATUS deprecated
	DESCRIPTION
		"This variable has been deprecated. A query will always 
		return -1.  The timeout value for persistence timeout for this
		application protocol session."
	::= { virtualServerEntry 6 }

virtualServerAppProtocolReaper OBJECT-TYPE
	SYNTAX INTEGER (0..65535)
	MAX-ACCESS read-only
	STATUS deprecated
	DESCRIPTION
		"This variable has been deprecated. A query will always 
		return -1.  The amount of idle time before we reap an 
		application protocol session."
	::= { virtualServerEntry 7 }

virtualServerPersistTimeout OBJECT-TYPE
	SYNTAX INTEGER
	MAX-ACCESS read-only
	STATUS current
	DESCRIPTION
		"The timeout value for persistence on this connection."
	::= { virtualServerEntry 8 }

virtualServerPersistMask OBJECT-TYPE
	SYNTAX IpAddress
	MAX-ACCESS read-only
	STATUS current
	DESCRIPTION
		"The IP addresses matching this mask will have persistent
		connections. Those not covered by this mask will not."
	::= { virtualServerEntry 9 }

virtualServerSticky OBJECT-TYPE
	SYNTAX INTEGER {
		true (1),
	false (2) }
	MAX-ACCESS read-only
	STATUS current
	DESCRIPTION
		"States whether destination address affinity is 
		turned on for this connection; true = yes, false = no." 
	::= { virtualServerEntry 10 }

virtualServerStickyMask OBJECT-TYPE
	SYNTAX IpAddress
	MAX-ACCESS read-only
	STATUS current
	DESCRIPTION
		"The addresses matching this mask will have destination
		address affinity if virtualServerSticky is true."
	::= { virtualServerEntry 11 }

virtualServerFailoverFlags OBJECT-TYPE
	SYNTAX INTEGER {
		mirrorconnections(1),
		mirrorpersistence(2),
		mirrorconnectionspersistence(3),
		nomirroring(4)
	}
	MAX-ACCESS read-only
	STATUS current
	DESCRIPTION
		"The fail-over flags for the this virtual server."
	::= { virtualServerEntry 12 }

virtualServerOctetsIn OBJECT-TYPE
	SYNTAX Counter32
	MAX-ACCESS read-only
	STATUS current
	DESCRIPTION
		"The number of octets received from the network from this
		virtual server."
	::= { virtualServerEntry 13 }

virtualServerOctetsOut OBJECT-TYPE
	SYNTAX Counter32
	MAX-ACCESS read-only
	STATUS current
	DESCRIPTION
		"The number of octets sent to the network from this virtual
		server."
	::= { virtualServerEntry 14 }

virtualServerPacketsIn OBJECT-TYPE
	SYNTAX Counter32
	MAX-ACCESS read-only
	STATUS current
	DESCRIPTION
		"The number of packets received from the network from this
		virtual server."
	::= { virtualServerEntry 15 }

virtualServerPacketsOut OBJECT-TYPE
	SYNTAX Counter32
	MAX-ACCESS read-only
	STATUS current
	DESCRIPTION
		"The number of packets sent to the network from this virtual
		server."
	::= { virtualServerEntry 16 }

virtualServerCurrentConn OBJECT-TYPE
	SYNTAX INTEGER (0..65535)
	MAX-ACCESS read-only
	STATUS current
	DESCRIPTION
		"The number of connections currently open on this virtual
		server."
	::= { virtualServerEntry 17 }

virtualServerMaxConn OBJECT-TYPE
	SYNTAX INTEGER (0..65535)
	MAX-ACCESS read-only
	STATUS current
	DESCRIPTION
		"The maximum number of connections this virtual server has had 
		open at any one time."
	::= { virtualServerEntry 18 }

virtualServerTotalConn OBJECT-TYPE
	SYNTAX Counter32
	MAX-ACCESS read-only
	STATUS current
	DESCRIPTION
		"The total number of connections this virtual server has
		served since the server started."
	::= { virtualServerEntry 19 }

virtualServerSslNew OBJECT-TYPE
	SYNTAX Counter32
	MAX-ACCESS read-only
	STATUS current
	DESCRIPTION
		"The number of new SSL sessions on this virtual server."
	::= { virtualServerEntry 20 }

virtualServerSslHits OBJECT-TYPE
	SYNTAX Counter32
	MAX-ACCESS read-only
	STATUS current
	DESCRIPTION
		"The number of lookup successes in the SSL session id
		cache for valid session ids."
	::= { virtualServerEntry 21 }

virtualServerSslTimeouts OBJECT-TYPE
	SYNTAX Counter32
	MAX-ACCESS read-only
	STATUS current
	DESCRIPTION
		"The number of lookup successes in the SSL session id
		cache for session ids that have already been reaped."
	::= { virtualServerEntry 22 }

virtualServerSslMisses OBJECT-TYPE
	SYNTAX Counter32
	MAX-ACCESS read-only
	STATUS current
	DESCRIPTION
		"The number of lookup failures in the SSL session id
		cache."
	::= { virtualServerEntry 23 }

virtualServerOctetsInHi32 OBJECT-TYPE
	SYNTAX Counter32
	MAX-ACCESS read-only
	STATUS current
	DESCRIPTION
		"The number of octets received from the network from this
		virtual server."
	::= { virtualServerEntry 24 }

virtualServerOctetsOutHi32 OBJECT-TYPE
	SYNTAX Counter32
	MAX-ACCESS read-only
	STATUS current
	DESCRIPTION
		"The number of octets sent to the network from this virtual
		server."
	::= { virtualServerEntry 25 }

virtualServerPacketsInHi32 OBJECT-TYPE
	SYNTAX Counter32
	MAX-ACCESS read-only
	STATUS current
	DESCRIPTION
		"The number of packets received from the network from this
		virtual server."
	::= { virtualServerEntry 26 }

virtualServerPacketsOutHi32 OBJECT-TYPE
	SYNTAX Counter32
	MAX-ACCESS read-only
	STATUS current
	DESCRIPTION
		"The number of packets sent to the network from this virtual
		server."
	::= { virtualServerEntry 27 }

virtualServerCookieMethod OBJECT-TYPE
	SYNTAX INTEGER {
		unspecified(1),
		insert(2),
		rewrite(3),
		passive(4),
		hash(5)
	}
	MAX-ACCESS read-only
	STATUS current
	DESCRIPTION
		"The cookie persistence method for this virtual server. This
		value is now set on the load balancing pool. This will always
		return unspecified(1)."
	::= { virtualServerEntry 28 }

virtualServerRule OBJECT-TYPE
	SYNTAX DisplayString (SIZE (0..255))
	MAX-ACCESS read-only
	STATUS current
	DESCRIPTION
		"The load balancing rule used by this virtual server."
	::= { virtualServerEntry 29 }

virtualServerPool OBJECT-TYPE
	SYNTAX DisplayString (SIZE (0..255))
	MAX-ACCESS read-only
	STATUS current
	DESCRIPTION
		"The load balancing pool used by this virtual server
		if a load balancing rule is not defined."
	::= { virtualServerEntry 30 }

virtualServerARPEnabled OBJECT-TYPE
	SYNTAX	INTEGER { true(1), false(2) }
	MAX-ACCESS read-only
	STATUS current
	DESCRIPTION
		"States whether ARP is enabled for this virtual 
		server; true = enabled, false = disabled."
	::= { virtualServerEntry 31 }

virtualServerLastHopPool OBJECT-TYPE
	SYNTAX DisplayString (SIZE (0..255))
	MAX-ACCESS read-only
	STATUS current
	DESCRIPTION
		"The load balancing pool used by this virtual server
		if traffic is transparent."
	::= { virtualServerEntry 32 }

virtualServerTranslateAddress OBJECT-TYPE
	SYNTAX	INTEGER { true(1), false(2) }
	MAX-ACCESS read-only
	STATUS current
	DESCRIPTION
		"States whether BIG-IP should translate virtual 
		server addresses; true = translate, false = no translate."
	::= { virtualServerEntry 33 }

virtualServerTranslatePort OBJECT-TYPE
	SYNTAX	INTEGER { true(1), false(2) }
	MAX-ACCESS read-only
	STATUS current
	DESCRIPTION
		"States whether port translation is enabled;
		true = enabled, false = disabled."
	::= { virtualServerEntry 34 }

virtualServerSvcDownReset OBJECT-TYPE
	SYNTAX	INTEGER { true(1), false(2) }
	MAX-ACCESS read-only
	STATUS current
	DESCRIPTION
		"States whether a reset is sent when service is 
		marked down; true = reset is sent, false = reset is not
		sent."
	::= { virtualServerEntry 35 }

virtualServerMayUseProxy OBJECT-TYPE
	SYNTAX	INTEGER { true(1), false(2) }
	MAX-ACCESS read-only
	STATUS current
	DESCRIPTION
		"States whether a virtual server will be associated 
		with an SSL proxy; true = yes, false = no."
	::= { virtualServerEntry 36 }

virtualServerAccelerate OBJECT-TYPE
	SYNTAX	INTEGER { true(1), false(2) }
	MAX-ACCESS read-only
	STATUS current
	DESCRIPTION
		"States whether the fast flow feature is enabled for 
		this virtual server; true = yes, false = no."
	::= { virtualServerEntry 37 }

virtualServerHCOctetsIn OBJECT-TYPE
	SYNTAX Counter64
	MAX-ACCESS read-only
	STATUS current
	DESCRIPTION
		"The number of octets received from the network from this
		virtual server."
	::= { virtualServerEntry 38 }

virtualServerHCOctetsOut OBJECT-TYPE
	SYNTAX Counter64
	MAX-ACCESS read-only
	STATUS current
	DESCRIPTION
		"The number of octets sent to the network from this virtual
		server."
	::= { virtualServerEntry 39 }

virtualServerHCPacketsIn OBJECT-TYPE
	SYNTAX Counter64
	MAX-ACCESS read-only
	STATUS current
	DESCRIPTION
		"The number of packets received from the network from this
		virtual server."
	::= { virtualServerEntry 40 }

virtualServerHCPacketsOut OBJECT-TYPE
	SYNTAX Counter64
	MAX-ACCESS read-only
	STATUS current
	DESCRIPTION
		"The number of packets sent to the network from this virtual
		server."
	::= { virtualServerEntry 41 }

--================================================================
-- SNAT Translation Address Table
--================================================================

snatTransTable OBJECT-TYPE
	SYNTAX SEQUENCE OF SnatTransEntry
	MAX-ACCESS not-accessible
	STATUS current
	DESCRIPTION
		"A table of all the secure NATS entries."
	::= { snat 1 }

snatTransEntry OBJECT-TYPE
	SYNTAX SnatTransEntry
	MAX-ACCESS not-accessible
	STATUS current
	DESCRIPTION "Columns in the table of secure NATS entries."
	INDEX { snatTransAddr }
	::= { snatTransTable 1 }

SnatTransEntry ::= SEQUENCE {
	snatTransEnabled		INTEGER,
	snatTransAddr			IpAddress,
	snatTransIface			DisplayString, -- deprecated and replaced by VLANs
	snatTransNetmask		IpAddress,
	snatTransBroadcast		IpAddress,
	snatTransSecsCollectingStats	Counter32,
	snatTransBitsIn			Counter32,
	snatTransBitsOut		Counter32,
	snatTransPktsIn			Counter32,
	snatTransPktsOut		Counter32,
	snatTransCurrConns		INTEGER,
	snatTransMaxConns		INTEGER,
	snatTransTotalConns		Counter32,
	snatTransBitsInHi32		Counter32,
	snatTransBitsOutHi32		Counter32,
	snatTransPktsInHi32		Counter32,
	snatTransPktsOutHi32		Counter32,
	snatTransLastTransPort		INTEGER,
	snatTransUnitId			INTEGER,
	snatTransVLANs			DisplayString,
	snatTransHCBitsIn		Counter64,
	snatTransHCBitsOut		Counter64,
	snatTransHCPktsIn		Counter64,
	snatTransHCPktsOut		Counter64
}
	
snatTransEnabled OBJECT-TYPE
	SYNTAX 	INTEGER {
		true(1),
		false(2)
	}
	MAX-ACCESS read-only
	STATUS current
	DESCRIPTION
		"States whether this TransAddress is enabled for SNAT;
		true = enabled, false = disabled."
	::= { snatTransEntry 1 }

snatTransAddr OBJECT-TYPE
	SYNTAX IpAddress
	MAX-ACCESS read-only
	STATUS current
	DESCRIPTION
		"The IP address to the outside world for this SNAT."
	::= { snatTransEntry 2 }
	
snatTransIface OBJECT-TYPE
	SYNTAX DisplayString (SIZE (0..10))
	MAX-ACCESS read-only
	STATUS deprecated
	DESCRIPTION
		"SNATs now exist on VLANS and not specific interfaces.
		This OID is deprecated and will always return 0.0.0.0."
	::= { snatTransEntry 3 }

snatTransNetmask OBJECT-TYPE
	SYNTAX IpAddress
	MAX-ACCESS read-only
	STATUS current
	DESCRIPTION
		"The network mask for the snatTransAddr."
	::= { snatTransEntry 4 }

snatTransBroadcast OBJECT-TYPE
	SYNTAX IpAddress
	MAX-ACCESS read-only
	STATUS current
	DESCRIPTION
		"The broadcast address for the snatTransAddr."
	::= { snatTransEntry 5 }

snatTransSecsCollectingStats OBJECT-TYPE
	SYNTAX Counter32
	MAX-ACCESS read-only
	STATUS current
	DESCRIPTION
		"The number of seconds we have been collecting
		 statistics for this port."
	::= { snatTransEntry 6 }

snatTransBitsIn OBJECT-TYPE
	SYNTAX Counter32
	MAX-ACCESS read-only
	STATUS current
	DESCRIPTION "The total bits in for this SNAT."
	::= { snatTransEntry 7 }

snatTransBitsOut OBJECT-TYPE
	SYNTAX Counter32
	MAX-ACCESS read-only
	STATUS current
	DESCRIPTION "The total bits out for this SNAT."
	::= { snatTransEntry 8 }

snatTransPktsIn OBJECT-TYPE
	SYNTAX Counter32
	MAX-ACCESS read-only
	STATUS current
	DESCRIPTION "The total packets in for this SNAT."
	::= { snatTransEntry 9 }

snatTransPktsOut OBJECT-TYPE
	SYNTAX Counter32
	MAX-ACCESS read-only
	STATUS current
	DESCRIPTION "The total packets out for this SNAT."
	::= { snatTransEntry 10 }

snatTransCurrConns OBJECT-TYPE
	SYNTAX INTEGER
	MAX-ACCESS read-only
	STATUS current
	DESCRIPTION "The number of connections currently open for this SNAT."
	::= { snatTransEntry 11 }

snatTransMaxConns OBJECT-TYPE
	SYNTAX INTEGER
	MAX-ACCESS read-only
	STATUS current
	DESCRIPTION "The maximum number of connections this SNAT
		has had open at any one time."
	::= { snatTransEntry 12 }

snatTransTotalConns OBJECT-TYPE
	SYNTAX Counter32
	MAX-ACCESS read-only
	STATUS current
	DESCRIPTION "The total number of connections this SNAT
		has had since the SNAT started."
	::= { snatTransEntry 13 }

snatTransBitsInHi32 OBJECT-TYPE
	SYNTAX Counter32
	MAX-ACCESS read-only
	STATUS current
	DESCRIPTION "The upper 32 bits of the total number of bits in for this SNAT."
	::= { snatTransEntry 14 }

snatTransBitsOutHi32 OBJECT-TYPE
	SYNTAX Counter32
	MAX-ACCESS read-only
	STATUS current
	DESCRIPTION "The upper 32 bits of the total number of bits out for 
		this SNAT."
	::= { snatTransEntry 15 }

snatTransPktsInHi32 OBJECT-TYPE
	SYNTAX Counter32
	MAX-ACCESS read-only
	STATUS current
	DESCRIPTION "The upper 32 bits of the total number of packets in 
		for this SNAT."
	::= { snatTransEntry 16 }

snatTransPktsOutHi32 OBJECT-TYPE
	SYNTAX Counter32
	MAX-ACCESS read-only
	STATUS current
	DESCRIPTION "The upper 32 bits of the total number of packets out 
		for this SNAT."
	::= { snatTransEntry 17 }

snatTransLastTransPort OBJECT-TYPE
	SYNTAX INTEGER
	MAX-ACCESS read-only
	STATUS current
	DESCRIPTION "Last translated port accessed using the SNAT."
	::= { snatTransEntry 18 }

snatTransUnitId OBJECT-TYPE
	SYNTAX INTEGER
	MAX-ACCESS read-only
	STATUS current
	DESCRIPTION "Unit number of the load balancer to which 
		the SNAT translation address is assigned."
	::= { snatTransEntry 19 }

snatTransVLANs OBJECT-TYPE
	SYNTAX DisplayString (SIZE (0..255))
	MAX-ACCESS read-only
	STATUS current
	DESCRIPTION  
		"If this list is empty, (the default) this secure 
		translation address  will be accessible on all VLANs. If 
		this list is not empty then this secure translation address 
		will be accessible only on those VLANs specified in the list."
	::= { snatTransEntry 20 }

snatTransHCBitsIn OBJECT-TYPE
	SYNTAX Counter64
	MAX-ACCESS read-only
	STATUS current
	DESCRIPTION "The total bits in for this SNAT."
	::= { snatTransEntry 21 }

snatTransHCBitsOut OBJECT-TYPE
	SYNTAX Counter64
	MAX-ACCESS read-only
	STATUS current
	DESCRIPTION "The total bits out for this SNAT."
	::= { snatTransEntry 22 }

snatTransHCPktsIn OBJECT-TYPE
	SYNTAX Counter64
	MAX-ACCESS read-only
	STATUS current
	DESCRIPTION "The total packets in for this SNAT."
	::= { snatTransEntry 23 }

snatTransHCPktsOut OBJECT-TYPE
	SYNTAX Counter64
	MAX-ACCESS read-only
	STATUS current
	DESCRIPTION "The total packets out for this SNAT."
	::= { snatTransEntry 24 }


--================================================================
-- SNAT Original Address Table
--================================================================
snatOrigTable OBJECT-TYPE
	SYNTAX SEQUENCE OF SnatOrigEntry
	MAX-ACCESS not-accessible
	STATUS current
	DESCRIPTION
		"A table of all the secure NATS entries."
	::= { snat 2 }

snatOrigEntry OBJECT-TYPE
	SYNTAX SnatOrigEntry
	MAX-ACCESS not-accessible
	STATUS current
	DESCRIPTION "Columns in the table of secure NATS entries."
	INDEX { snatOrigAddr }
	::= { snatOrigTable 1 }

SnatOrigEntry ::= SEQUENCE {
	snatOrigEnabled			INTEGER,
	snatOrigAddr			IpAddress,
	snatOrigConnLimit		INTEGER,
	snatOrigTransAddr		IpAddress,
	snatOrigTcpIdleTimeout		Counter32,
	snatOrigUdpIdleTimeout		Counter32,
	snatOrigStatsZeroTime		Counter32,
	snatOrigSecsCollectingStats	Counter32,
	snatOrigBitsIn			Counter32,
	snatOrigBitsOut			Counter32,
	snatOrigPktsIn			Counter32,
	snatOrigPktsOut			Counter32,
	snatOrigCurrConns		INTEGER,
	snatOrigMaxConns		INTEGER,
	snatOrigTotalConns		Counter32,
	snatOrigBitsInHi32		Counter32,
	snatOrigBitsOutHi32		Counter32,
	snatOrigPktsInHi32		Counter32,
	snatOrigPktsOutHi32		Counter32,
	snatOrigLastTransPort		INTEGER,
	snatOrigHCBitsIn		Counter64,
	snatOrigHCBitsOut		Counter64,
	snatOrigHCPktsIn		Counter64,
	snatOrigHCPktsOut		Counter64
}
	
snatOrigEnabled OBJECT-TYPE
	SYNTAX 	TruthValue
	MAX-ACCESS read-only
	STATUS current
	DESCRIPTION
		"States whether this OrigAddress is enabled for SNAT;
		true = enabled, false = disabled."
	::= { snatOrigEntry 1 }

snatOrigAddr OBJECT-TYPE
	SYNTAX IpAddress
	MAX-ACCESS read-only
	STATUS current
	DESCRIPTION
		"The IP address to the outside world for this SNAT."
	::= { snatOrigEntry 2 }

snatOrigConnLimit OBJECT-TYPE
	SYNTAX INTEGER
	MAX-ACCESS read-only
	STATUS current
	DESCRIPTION
		"The maximum number of connections through this snat."
	::= { snatOrigEntry 3 }

snatOrigTransAddr OBJECT-TYPE
	SYNTAX IpAddress
	MAX-ACCESS read-only
	STATUS current
	DESCRIPTION
		"The translation address corresponding to this
		original address."
	::= { snatOrigEntry 4 }

snatOrigTcpIdleTimeout OBJECT-TYPE
	SYNTAX Counter32
	MAX-ACCESS read-only
	STATUS current
	DESCRIPTION
		"The idle timeout value for TCP connections through this SNAT."
	::= { snatOrigEntry 5 }

snatOrigUdpIdleTimeout OBJECT-TYPE
	SYNTAX Counter32
	MAX-ACCESS read-only
	STATUS current
	DESCRIPTION
		"The idle timeout value for TCP connections through this SNAT."
	::= { snatOrigEntry 6 }

snatOrigStatsZeroTime OBJECT-TYPE
	SYNTAX Counter32
	MAX-ACCESS read-only
	STATUS current
	DESCRIPTION
		"The time the BIG-IP started collecting statistics for this 
		port."
	::= { snatOrigEntry 7 }

snatOrigSecsCollectingStats OBJECT-TYPE
	SYNTAX Counter32
	MAX-ACCESS read-only
	STATUS current
	DESCRIPTION
		"The number of seconds the BIG-IP has been collecting
		 statistics for this port."
	::= { snatOrigEntry 8 }

snatOrigBitsIn OBJECT-TYPE
	SYNTAX Counter32
	MAX-ACCESS read-only
	STATUS current
	DESCRIPTION
		"The number of bits received on this snat.  If the count
		overflows a 32 bit value, this contains the lower 32 bits
		of a 64 bit counter with the upper 32 bits contained in 
		snatOrigBitsInHi32."
	::= { snatOrigEntry 9 }

snatOrigBitsOut OBJECT-TYPE
	SYNTAX Counter32
	MAX-ACCESS read-only
	STATUS current
	DESCRIPTION
		"The number of bits sent on this snat.  If the count
		overflows a 32 bit value, this contains the lower 32 bits
		of a 64 bit counter with the upper 32 bits contained in 
		snatOrigBitsOutHi32."
	::= { snatOrigEntry 10 }

snatOrigPktsIn OBJECT-TYPE
	SYNTAX Counter32
	MAX-ACCESS read-only
	STATUS current
	DESCRIPTION
		"The number of packets received on this snat.  If the count
		overflows a 32 bit value, this contains the lower 32 bits
		of a 64 bit counter with the upper 32 bits contained in 
		snatOrigPktsInHi32."
	::= { snatOrigEntry 11 }

snatOrigPktsOut OBJECT-TYPE
	SYNTAX Counter32
	MAX-ACCESS read-only
	STATUS current
	DESCRIPTION 
		"The number of packets sent on this snat.  If the count
		overflows a 32 bit value, this contains the lower 32 bits
		of a 64 bit counter with the upper 32 bits contained in 
		snatOrigPktsOutHi32."
	::= { snatOrigEntry 12 }

snatOrigCurrConns OBJECT-TYPE
	SYNTAX INTEGER
	MAX-ACCESS read-only
	STATUS current
	DESCRIPTION "The current number of connections for this SNAT."
	::= { snatOrigEntry 13 }

snatOrigMaxConns OBJECT-TYPE
	SYNTAX INTEGER
	MAX-ACCESS read-only
	STATUS current
	DESCRIPTION "The maximum number of connections this SNAT has
		had at any one time."
	::= { snatOrigEntry 14 }

snatOrigTotalConns OBJECT-TYPE
	SYNTAX Counter32 
	MAX-ACCESS read-only
	STATUS current
	DESCRIPTION "The total number of connections this SNAT has
		had since the SNAT started."

	::= { snatOrigEntry 15 }

snatOrigBitsInHi32 OBJECT-TYPE
	SYNTAX Counter32
	MAX-ACCESS read-only
	STATUS current
	DESCRIPTION 
		"The total number of bits in for this SNAT (High order 32)."
	::= { snatOrigEntry 16 }

snatOrigBitsOutHi32 OBJECT-TYPE
	SYNTAX Counter32
	MAX-ACCESS read-only
	STATUS current
	DESCRIPTION 
		"The total number of bits out for this SNAT (High order 32)."
	::= { snatOrigEntry 17 }

snatOrigPktsInHi32 OBJECT-TYPE
	SYNTAX Counter32
	MAX-ACCESS read-only
	STATUS current
	DESCRIPTION "The upper 32 bits of the total number of packets in 
		for this SNAT."
	::= { snatOrigEntry 18 }

snatOrigPktsOutHi32 OBJECT-TYPE
	SYNTAX Counter32
	MAX-ACCESS read-only
	STATUS current
	DESCRIPTION "The upper 32 bits of the total number of packets out 
		for this SNAT."
	::= { snatOrigEntry 19 }

snatOrigLastTransPort OBJECT-TYPE
	SYNTAX INTEGER
	MAX-ACCESS read-only
	STATUS current
	DESCRIPTION "Last translated port accessed using the SNAT."
	::= { snatOrigEntry 20 }

snatOrigHCBitsIn OBJECT-TYPE
	SYNTAX Counter64
	MAX-ACCESS read-only
	STATUS current
	DESCRIPTION
		"The number of bits received on this snat."
	::= { snatOrigEntry 21 }

snatOrigHCBitsOut OBJECT-TYPE
	SYNTAX Counter64
	MAX-ACCESS read-only
	STATUS current
	DESCRIPTION
		"The number of bits sent on this snat."
	::= { snatOrigEntry 22 }

snatOrigHCPktsIn OBJECT-TYPE
	SYNTAX Counter64
	MAX-ACCESS read-only
	STATUS current
	DESCRIPTION
		"The number of packets received on this snat."
	::= { snatOrigEntry 23 }

snatOrigHCPktsOut OBJECT-TYPE
	SYNTAX Counter64
	MAX-ACCESS read-only
	STATUS current
	DESCRIPTION 
		"The number of packets sent on this snat."
	::= { snatOrigEntry 24 }

--================================================================
-- General BIG-IP Scalars
--================================================================
uptime OBJECT-TYPE
	SYNTAX TimeTicks
	MAX-ACCESS read-only
	STATUS deprecated
	DESCRIPTION
	"This OID is deprecated. See globalStatUptime.
	The uptime of this device -- not the uptime of the SNMP agent."
	::= { loadbal 50 }

contot OBJECT-TYPE
	SYNTAX Counter32
	MAX-ACCESS read-only
	STATUS deprecated
	DESCRIPTION
	"This OID is deprecated. See globalStatTotalConn.
	The total number of connections this balancer has serviced."
	::= { loadbal 51 }

concur OBJECT-TYPE
	SYNTAX INTEGER
	MAX-ACCESS read-only
	STATUS deprecated
	DESCRIPTION
	"This OID is deprecated. See globalStatCurrentConn.
	The number of current connections."
	::= { loadbal 52 }

conmax OBJECT-TYPE
	SYNTAX INTEGER
	MAX-ACCESS read-only
	STATUS deprecated
	DESCRIPTION
	"This OID is deprecated. See globalStatMaxConn.  The maximum 
	number of connections that this balancer has serviced at one time."
	::= { loadbal 53 }

pktsin OBJECT-TYPE
	SYNTAX Counter32
	MAX-ACCESS read-only
	STATUS deprecated
	DESCRIPTION
	"This OID is deprecated. See globalStatPcktsin.
	The total count of all packets read off the network."
	::= { loadbal 54 }

pktsout OBJECT-TYPE
	SYNTAX Counter32
	MAX-ACCESS read-only
	STATUS deprecated
	DESCRIPTION
	"This OID is deprecated. See globalStatPcktsout.
	The total count of all packets written to the network."
	::= { loadbal 55 }

bitsin OBJECT-TYPE
	SYNTAX Counter32
	MAX-ACCESS read-only
	STATUS deprecated
	DESCRIPTION
	"This OID is deprecated. See globalStatBitsin.
	The total number of bits read off the network."
	::= { loadbal 56 }

bitsout OBJECT-TYPE
	SYNTAX Counter32
	MAX-ACCESS read-only
	STATUS deprecated
	DESCRIPTION
	"This OID is deprecated. See globalStatBitsout.
	The total count of all bits written to the network."
	::= { loadbal 57 }

portdeny OBJECT-TYPE
	SYNTAX Counter32
	MAX-ACCESS read-only
	STATUS current
	DESCRIPTION
		"The count of port denies that has occurred."
	::= { loadbal 58 }

droppedin OBJECT-TYPE
	SYNTAX Counter32
	MAX-ACCESS read-only
	STATUS current
	DESCRIPTION
		"The count of inbound packets that have been dropped."
	::= { loadbal 59 }

droppedout OBJECT-TYPE
	SYNTAX Counter32
	MAX-ACCESS read-only
	STATUS current
	DESCRIPTION
		"The count of outbound packets that have been dropped."
	::= { loadbal 60 }

active OBJECT-TYPE
	SYNTAX INTEGER {
		standby (1),
		active (2),
		unsupported (99) }
	MAX-ACCESS read-only
	STATUS deprecated
	DESCRIPTION
	"This OID is deprecated. See globalAttrMaster.
	Mode of this BIG-IP: active or standby."
	::= { loadbal 61 }

mirrorenabled OBJECT-TYPE
	SYNTAX INTEGER {
		disabled (1),
		enabled (2),
		unsupported (99) }
	MAX-ACCESS read-only
	STATUS deprecated
	DESCRIPTION
	"This OID is deprecated. See globalAttrMirrorEnabled.
	State of mirroring on this BIG-IP: enabled
	or disabled. This OID does not apply to 3-DNS."
	::= { loadbal 62 }

resetcounters OBJECT-TYPE
	SYNTAX INTEGER {
		unreset(2),
		reset (1),
		unsupported(99)
	}
	MAX-ACCESS read-write
	STATUS current
	DESCRIPTION
		"Setting this value to reset(1) will set the BIG-IP 
		traffic counters to 0."
	::= { loadbal 63 }

pktsinHi32 OBJECT-TYPE
	SYNTAX Counter32
	MAX-ACCESS read-only
	STATUS deprecated
	DESCRIPTION
	"This OID is deprecated. See globalStatPcktsinHi32.
	The total count of all packets read off the network."
	::= { loadbal 64 }

pktsoutHi32 OBJECT-TYPE
	SYNTAX Counter32
	MAX-ACCESS read-only
	STATUS deprecated
	DESCRIPTION
	"This OID is deprecated. See globalStatPcktsoutHi32.
	The total count of all packets written to the network."
	::= { loadbal 65 }

bitsinHi32 OBJECT-TYPE
	SYNTAX Counter32
	MAX-ACCESS read-only
	STATUS deprecated
	DESCRIPTION
	"This OID is deprecated. See globalStatBitsinHi32.
	The total number of bits read off the network."
	::= { loadbal 66 }

bitsoutHi32 OBJECT-TYPE
	SYNTAX Counter32
	MAX-ACCESS read-only
	STATUS deprecated
	DESCRIPTION
		"This OID is deprecated. See globalStatBitsoutHi32.
	The total count of all bits written to the network."
	::= { loadbal 67 }

nodePing OBJECT-TYPE
	SYNTAX INTEGER
	MAX-ACCESS read-only
	STATUS deprecated
	DESCRIPTION
		"This OID is deprecated. Node ping interval in seconds."
	::= { loadbal 68 }

nodeTimeout OBJECT-TYPE
	SYNTAX INTEGER
	MAX-ACCESS read-only
	STATUS deprecated
	DESCRIPTION
		"This OID is deprecated. Node timeout interval in seconds."
	::= { loadbal 69 }

loadbalMode OBJECT-TYPE
	SYNTAX INTEGER {
		roundrobin(1),
		ratioMember(2),
		leastConnMember(3),
		observedMember(4),
		predictiveMember(5),
		ratioNodeAddress(6),
		leastConnNodeAddress(7),
		fastestNodeAddress(8),
		observerdNodeAddress(9),
		predictiveNodeAddress(10),
		dynamicRatio(11),
		fastestAppResponse(12),
		unsupported(99)
	}
	MAX-ACCESS read-only
	STATUS current
	DESCRIPTION
		"The global load balance mode.
		This OID does not apply to 3-DNS."
	::= { loadbal 70 }

watchDogArmed OBJECT-TYPE
	SYNTAX INTEGER {
		armed(1), disarmed(2), unsupported(99)
	}
	MAX-ACCESS read-only
	STATUS deprecated
	DESCRIPTION
	"This OID is deprecated. See globalAttrWatchDogArmed.
	Watch dog card state."
	::= { loadbal 71 }

snatConnLimit OBJECT-TYPE
	SYNTAX INTEGER 
	MAX-ACCESS read-only
	STATUS deprecated
	DESCRIPTION
	"This OID is deprecated. See globalAttrSNATConnLimit.
	Number of simultaneous connections allowed through a SNAT.
	This OID does not apply to 3-DNS."
	::= { loadbal 72 }

snatTCPIdleTimeout OBJECT-TYPE
	SYNTAX INTEGER 
	MAX-ACCESS read-only
	STATUS deprecated
	DESCRIPTION
	"This OID is deprecated. See globalAttrSNATTCPIdleTimeout.
	Default connection timeout for SNAT TCP connections.
	This OID does not apply to 3-DNS."
	::= { loadbal 73 }

snatUDPIdleTimeout OBJECT-TYPE
	SYNTAX INTEGER 
	MAX-ACCESS read-only
	STATUS deprecated
	DESCRIPTION
	"This OID is deprecated. See globalAttrSNATUDPIdleTimeout.
	Default timeout for SNAT UDP connections.
	This OID does not apply to 3-DNS."
	::= { loadbal 74 }

gatewayFailsafe OBJECT-TYPE
	SYNTAX INTEGER {
		enabled(1),
		disabled(2),
		unsupported(99)
	}
	MAX-ACCESS read-only
	STATUS deprecated
	DESCRIPTION
	"This OID is deprecated. See globalAttrGatewayFailsafeArmed.
	Is gateway failsafe pinging enabled."
	::= { loadbal 75 }

unitId OBJECT-TYPE
	SYNTAX DisplayString (SIZE (0..255))
	MAX-ACCESS read-only
	STATUS deprecated
	DESCRIPTION
	"This OID is deprecated. See globalAttrUnitID.
	Unit id(s) for this load balancer."
	::= { loadbal 76 }

memoryUsed OBJECT-TYPE
	SYNTAX INTEGER
	MAX-ACCESS read-only
	STATUS deprecated
	DESCRIPTION
	"This OID is deprecated. See globalStatMemoryPoolUsed.
	Memory used by the load balancer kernel."
	::= { loadbal 77 }
 
memoryTotal OBJECT-TYPE
	SYNTAX INTEGER
	MAX-ACCESS read-only
	STATUS deprecated
	DESCRIPTION
	"This OID is deprecated. See globalStatMemoryPoolTotal.
	Total memory available to the load balancer kernel."
	::= { loadbal 78 }

cpuTemperature OBJECT-TYPE
	SYNTAX INTEGER
	MAX-ACCESS read-only
	STATUS deprecated
	DESCRIPTION
		"This OID is deprecated."
	::= { loadbal 79 }

fanSpeed OBJECT-TYPE
	SYNTAX INTEGER
	MAX-ACCESS read-only
	STATUS deprecated
	DESCRIPTION
		"This OID is deprecated."
	::= { loadbal 80 }

multiprocessingMode OBJECT-TYPE
	SYNTAX INTEGER { up(1), anip(2), smp(3), unsupported(99) }
	MAX-ACCESS read-only
	STATUS deprecated
	DESCRIPTION
	"This OID is deprecated. See globalStatMultiProcessorMode.
	The current multiprocessing mode of this BIG-IP.
	There are three possible multiprocessing modes for a BIG-IP.
	up(1) is the uniprocessor mode. The BIG-IP will always initially
	startup in this mode. During boot the BIG-IP if it is configured for
	and capable of multiprocessing will switch to either ANIP(2), or SMP(3)
	modes. ANIP is the auxiliary network interface mode. SMP is the symmetric
	multiprocessor mode."
	::= { loadbal 81 }

percentANIP OBJECT-TYPE
	SYNTAX INTEGER 
	MAX-ACCESS read-only
	STATUS deprecated
	DESCRIPTION
	"This OID is deprecated. See globalStatANIPPercent.  Percentage of time 
	the ANIP(auxiliary network interface processor) is doing useful work."
	::= { loadbal 82 }

cpuCount OBJECT-TYPE
	SYNTAX INTEGER
	MAX-ACCESS read-only
	STATUS deprecated
	DESCRIPTION
	"This OID is deprecated. See globalStatCPUCount.
	The number of CPUs present on this BIG-IP."
	::= { loadbal 83 }


--================================================================
-- VADDRESS (Virtual Address) information
--================================================================
vaddressNumber OBJECT-TYPE
	SYNTAX INTEGER
	MAX-ACCESS read-only
	STATUS current
	DESCRIPTION
		"The number of virtual IP addresses present on this system."
	::= { vaddress 1 }

vaddressTable OBJECT-TYPE
	SYNTAX SEQUENCE OF VaddressEntry
	MAX-ACCESS not-accessible
	STATUS current
	DESCRIPTION
		"A list of virtual IP addresses. The number of
		entries is given by the value of vaddressNumber."
	::= { vaddress 2 }

vaddressEntry OBJECT-TYPE
	SYNTAX VaddressEntry
	MAX-ACCESS not-accessible
	STATUS current
	DESCRIPTION
		"A table entry containing virtual address information."
	INDEX { vaddressIndex }
	::= { vaddressTable 1 }

VaddressEntry ::=
	SEQUENCE {
		vaddressIndex		INTEGER,
		vaddressDescr		DisplayString,
		vaddressIpAddr		IpAddress,
		vaddressPktsin		Counter32,
		vaddressPktsout		Counter32,
		vaddressBitsin		Counter32,
		vaddressBitsout		Counter32,
		vaddressConcur		INTEGER,
		vaddressConmax		INTEGER,
		vaddressConlimit	INTEGER,
		vaddressContot		Counter32,
		vaddressStatus		INTEGER,
		vaddressPktsinHi32	Counter32,
		vaddressPktsoutHi32	Counter32,
		vaddressBitsinHi32	Counter32,
		vaddressBitsoutHi32	Counter32,
		vaddressHCPktsin	Counter64,
		vaddressHCPktsout	Counter64,
		vaddressHCBitsin	Counter64,
		vaddressHCBitsout	Counter64
	}

vaddressIndex OBJECT-TYPE
	SYNTAX INTEGER (0..65535)
	MAX-ACCESS read-only
	STATUS current
	DESCRIPTION
		"A unique value for each virtual address defined."
	::= { vaddressEntry 1 }

vaddressDescr OBJECT-TYPE
	SYNTAX DisplayString (SIZE (0..255))
	MAX-ACCESS read-only
	STATUS current
	DESCRIPTION
		"A textual string describing the virtual address."
	::= { vaddressEntry 2 }

vaddressIpAddr OBJECT-TYPE
	SYNTAX IpAddress
	MAX-ACCESS read-only
	STATUS current
	DESCRIPTION
		"The IP address for this virtual address."
	::= { vaddressEntry 3 }

vaddressPktsin OBJECT-TYPE
	SYNTAX Counter32
	MAX-ACCESS read-only
	STATUS current
	DESCRIPTION
		"The total packets in for this virtual address."
	::= { vaddressEntry 4 }

vaddressPktsout OBJECT-TYPE
	SYNTAX Counter32
	MAX-ACCESS read-only
	STATUS current
	DESCRIPTION
		"The total packets out of this virtual address."
	::= { vaddressEntry 5 }

vaddressBitsin OBJECT-TYPE
	SYNTAX Counter32
	MAX-ACCESS read-only
	STATUS current
	DESCRIPTION
		"The total bits in for this virtual address."
	::= { vaddressEntry 6 }

vaddressBitsout OBJECT-TYPE
	SYNTAX Counter32
	MAX-ACCESS read-only
	STATUS current
	DESCRIPTION
		"The total bits out of this virtual address."
	::= { vaddressEntry 7 }

vaddressConcur OBJECT-TYPE
	SYNTAX INTEGER
	MAX-ACCESS read-only
	STATUS current
	DESCRIPTION
		"The current number of connections on this virtual
		address."
	::= { vaddressEntry 8 }

vaddressConmax OBJECT-TYPE
	SYNTAX INTEGER
	MAX-ACCESS read-only
	STATUS current
	DESCRIPTION
		"The maximum number of connections this virtual server
		has had open at any one time."
	::= { vaddressEntry 9 }

vaddressConlimit OBJECT-TYPE
	SYNTAX INTEGER
	MAX-ACCESS read-only
	STATUS current
	DESCRIPTION
		"The total number of connections this virtual address
	can support at one time."
	::= { vaddressEntry 10 }

vaddressContot OBJECT-TYPE
	SYNTAX Counter32
	MAX-ACCESS read-only
	STATUS current
	DESCRIPTION
		"The total number of connections this virtual server
		has served since the server started."
	::= { vaddressEntry 11 }

vaddressStatus OBJECT-TYPE
	SYNTAX INTEGER {
		ready(1),
		maintenance(2)
	}
	MAX-ACCESS read-only
	STATUS current
	DESCRIPTION
		"Status of this virtual address."
	::= { vaddressEntry 12 }

vaddressPktsinHi32 OBJECT-TYPE
	SYNTAX Counter32
	MAX-ACCESS read-only
	STATUS current
	DESCRIPTION
		"The total packets in for this virtual address."
	::= { vaddressEntry 13 }

vaddressPktsoutHi32 OBJECT-TYPE
	SYNTAX Counter32
	MAX-ACCESS read-only
	STATUS current
	DESCRIPTION
		"The total packets out of this virtual address."
	::= { vaddressEntry 14 }

vaddressBitsinHi32 OBJECT-TYPE
	SYNTAX Counter32
	MAX-ACCESS read-only
	STATUS current
	DESCRIPTION
		"The total bits in for this virtual address."
	::= { vaddressEntry 15 }

vaddressBitsoutHi32 OBJECT-TYPE
	SYNTAX Counter32
	MAX-ACCESS read-only
	STATUS current
	DESCRIPTION
		"The total bits out of this virtual address."
	::= { vaddressEntry 16 }

vaddressHCPktsin OBJECT-TYPE
	SYNTAX Counter64
	MAX-ACCESS read-only
	STATUS current
	DESCRIPTION
		"The total packets in for this virtual address."
	::= { vaddressEntry 17 }

vaddressHCPktsout OBJECT-TYPE
	SYNTAX Counter64
	MAX-ACCESS read-only
	STATUS current
	DESCRIPTION
		"The total packets out of this virtual address."
	::= { vaddressEntry 18 }

vaddressHCBitsin OBJECT-TYPE
	SYNTAX Counter64
	MAX-ACCESS read-only
	STATUS current
	DESCRIPTION
		"The total bits in for this virtual address."
	::= { vaddressEntry 19 }

vaddressHCBitsout OBJECT-TYPE
	SYNTAX Counter64
	MAX-ACCESS read-only
	STATUS current
	DESCRIPTION
		"The total bits out of this virtual address."
	::= { vaddressEntry 20 }


--================================================================
-- NDADDR information
--================================================================
ndaddrNumber OBJECT-TYPE
	SYNTAX INTEGER
	MAX-ACCESS read-only
	STATUS current
	DESCRIPTION
		"The number of node addresses present on this system."
	::= { ndaddr 1 }

ndaddrTable OBJECT-TYPE
	SYNTAX SEQUENCE OF NdaddrEntry
	MAX-ACCESS not-accessible
	STATUS current
	DESCRIPTION
		"A list of ndaddr entries. The number of entries is
		given by the value of ndaddrNumber."
	::= { ndaddr 2 }

ndaddrEntry OBJECT-TYPE
	SYNTAX NdaddrEntry
	MAX-ACCESS not-accessible
	STATUS current
	DESCRIPTION
		"A ndaddr entry containing ndaddr statistics."
	INDEX { ndaddrIndex }
	::= { ndaddrTable 1 }

NdaddrEntry ::=
	SEQUENCE {
		ndaddrIndex	INTEGER,
		ndaddrDescr	DisplayString,
		ndaddrIpAddr	IpAddress,
		ndaddrPktsin	Counter32,
		ndaddrPktsout	Counter32,
		ndaddrBitsin	Counter32,
		ndaddrBitsout	Counter32,
		ndaddrConcur	INTEGER,
		ndaddrConmax	INTEGER,
		ndaddrConlimit	INTEGER,
		ndaddrContot	Counter32,
		ndaddrStatus	INTEGER,
		ndaddrPktsinHi32	Counter32,
		ndaddrPktsoutHi32	Counter32,
		ndaddrBitsinHi32	Counter32,
		ndaddrBitsoutHi32	Counter32,
		ndaddrMaintenance	INTEGER,
		ndaddrIsVirtual		INTEGER,
		ndaddrRatio		INTEGER,
		ndaddrTotalRealMemory	INTEGER,
		ndaddrAvailableRealMemory	INTEGER,
		ndaddrTotalDisk		INTEGER,
		ndaddrAvailableDisk	INTEGER,
		ndaddrAvailableCPU	INTEGER,
		ndaddrDynamicRatio	INTEGER,
		ndaddrPingerState	INTEGER,
		ndaddrHCPktsin		Counter64,
		ndaddrHCPktsout		Counter64,
		ndaddrHCBitsin		Counter64,
		ndaddrHCBitsout		Counter64
	}

ndaddrIndex OBJECT-TYPE
	SYNTAX INTEGER (0..65535)
	MAX-ACCESS read-only
	STATUS current
	DESCRIPTION
		"A unique value for each ndaddr defined."
	::= { ndaddrEntry 1 }

ndaddrDescr OBJECT-TYPE
	SYNTAX DisplayString (SIZE (0..255))
	MAX-ACCESS read-only
	STATUS current
	DESCRIPTION
		"A textual string describing the node address."
	::= { ndaddrEntry 2 }

ndaddrIpAddr OBJECT-TYPE
	SYNTAX IpAddress
	MAX-ACCESS read-only
	STATUS current
	DESCRIPTION
		"The Node address (IP Address)."
	::= { ndaddrEntry 3 }

ndaddrPktsin OBJECT-TYPE
	SYNTAX Counter32
	MAX-ACCESS read-only
	STATUS current
	DESCRIPTION
		"The total packets in for this node address."
	::= { ndaddrEntry 4 }

ndaddrPktsout OBJECT-TYPE
	SYNTAX Counter32
	MAX-ACCESS read-only
	STATUS current
	DESCRIPTION
		"The total packets out for this node address."
	::= { ndaddrEntry 5 }

ndaddrBitsin OBJECT-TYPE
	SYNTAX Counter32
	MAX-ACCESS read-only
	STATUS current
	DESCRIPTION
		"The total bits in for this node address."
	::= { ndaddrEntry 6 }

ndaddrBitsout OBJECT-TYPE
	SYNTAX Counter32
	MAX-ACCESS read-only
	STATUS current
	DESCRIPTION
		"The total bits out for this node address."
	::= { ndaddrEntry 7 }

ndaddrConcur OBJECT-TYPE
	SYNTAX INTEGER
	MAX-ACCESS read-only
	STATUS current
	DESCRIPTION
		"The number of current connections for this node
		address."
	::= { ndaddrEntry 8 }

ndaddrConmax OBJECT-TYPE
	SYNTAX INTEGER
	MAX-ACCESS read-only
	STATUS current
	DESCRIPTION
		"The maximum number of connections this node address
		has had open at one time."
	::= { ndaddrEntry 9 }

ndaddrConlimit OBJECT-TYPE
	SYNTAX INTEGER
	MAX-ACCESS read-only
	STATUS current
	DESCRIPTION
		"The maximum number of connections this node address
		is allowed to have open at one time."
	::= { ndaddrEntry 10 }

ndaddrContot OBJECT-TYPE
	SYNTAX Counter32
	MAX-ACCESS read-only
	STATUS current
	DESCRIPTION
		"The total connections that this node address had
		had."
	::= { ndaddrEntry 11 }

ndaddrStatus OBJECT-TYPE
	SYNTAX BigAPIStatus
	MAX-ACCESS read-only
	STATUS current
	DESCRIPTION
		"The status of this node address."
	::= { ndaddrEntry 12 }

ndaddrPktsinHi32 OBJECT-TYPE
	SYNTAX Counter32
	MAX-ACCESS read-only
	STATUS current
	DESCRIPTION
		"The total packets in for this node address."
	::= { ndaddrEntry 13 }

ndaddrPktsoutHi32 OBJECT-TYPE
	SYNTAX Counter32
	MAX-ACCESS read-only
	STATUS current
	DESCRIPTION
		"The total packets out for this node address."
	::= { ndaddrEntry 14 }

ndaddrBitsinHi32 OBJECT-TYPE
	SYNTAX Counter32
	MAX-ACCESS read-only
	STATUS current
	DESCRIPTION
		"The total bits in for this node address."
	::= { ndaddrEntry 15 }

ndaddrBitsoutHi32 OBJECT-TYPE
	SYNTAX Counter32
	MAX-ACCESS read-only
	STATUS current
	DESCRIPTION
		"The total bits out for this node address."
	::= { ndaddrEntry 16 }

ndaddrMaintenance OBJECT-TYPE
	SYNTAX INTEGER {
		true(1),
		false(2)
	}
	MAX-ACCESS read-only
	STATUS current
	DESCRIPTION
		"States whether this node address is in maintenance 
		mode; true = maintenance mode, false = no maintenance mode."
	::= { ndaddrEntry 17 }

ndaddrIsVirtual OBJECT-TYPE
	SYNTAX INTEGER {
		true(1),
		false(2)
	}
	MAX-ACCESS read-only
	STATUS current
	DESCRIPTION
		"States whether the node server is on a different 
		BIG-IP; true = yes, false = no."
	::= { ndaddrEntry 18 }

ndaddrRatio OBJECT-TYPE
	SYNTAX INTEGER 
	MAX-ACCESS read-only
	STATUS current
	DESCRIPTION
		"Node address ratio, used is load balance algorithm."
	::= { ndaddrEntry 19 }

ndaddrTotalRealMemory OBJECT-TYPE
	SYNTAX INTEGER 
	MAX-ACCESS read-only
	STATUS current
	DESCRIPTION
		"Node address, total real memory in KB."
	::= { ndaddrEntry 20 }

ndaddrAvailableRealMemory OBJECT-TYPE
	SYNTAX INTEGER 
	MAX-ACCESS read-only
	STATUS current
	DESCRIPTION
		"Node address, total available real memory in KB."
	::= { ndaddrEntry 21 }

ndaddrTotalDisk OBJECT-TYPE
	SYNTAX INTEGER 
	MAX-ACCESS read-only
	STATUS current
	DESCRIPTION
		"Node address, total available disk space in KB."
	::= { ndaddrEntry 22 }

ndaddrAvailableDisk OBJECT-TYPE
	SYNTAX INTEGER 
	MAX-ACCESS read-only
	STATUS current
	DESCRIPTION
		"Node address, available disk space in KB."
	::= { ndaddrEntry 23 }

ndaddrAvailableCPU OBJECT-TYPE
	SYNTAX INTEGER 
	MAX-ACCESS read-only
	STATUS current
	DESCRIPTION
		"Node address, percentage of CPU available."
	::= { ndaddrEntry 24 }

ndaddrDynamicRatio OBJECT-TYPE
	SYNTAX INTEGER 
	MAX-ACCESS read-only
	STATUS current
	DESCRIPTION
		"Node address, dynamic ratio, used in load balance algorithm."
	::= { ndaddrEntry 25 }

ndaddrPingerState OBJECT-TYPE
	SYNTAX INTEGER {
		unchecked(1),
		up(2),
		down(3),
		forcedDown(4),
		checking(5)
	}
	MAX-ACCESS read-only
	STATUS current
	DESCRIPTION
		"Enumerated type, describing node server state, up, down 
                 checking, unchecked."
	::= { ndaddrEntry 26 }

ndaddrHCPktsin OBJECT-TYPE
	SYNTAX Counter64
	MAX-ACCESS read-only
	STATUS current
	DESCRIPTION
		"The total packets in for this node address."
	::= { ndaddrEntry 27 }

ndaddrHCPktsout OBJECT-TYPE
	SYNTAX Counter64
	MAX-ACCESS read-only
	STATUS current
	DESCRIPTION
		"The total packets out for this node address."
	::= { ndaddrEntry 28 }

ndaddrHCBitsin OBJECT-TYPE
	SYNTAX Counter64
	MAX-ACCESS read-only
	STATUS current
	DESCRIPTION
		"The total bits in for this node address."
	::= { ndaddrEntry 29 }

ndaddrHCBitsout OBJECT-TYPE
	SYNTAX Counter64
	MAX-ACCESS read-only
	STATUS current
	DESCRIPTION
		"The total bits out for this node address."
	::= { ndaddrEntry 30 }

--================================================================
-- NAT (Network Address Translation) information
--================================================================
natNumber OBJECT-TYPE
	SYNTAX INTEGER
	MAX-ACCESS read-only
	STATUS current
	DESCRIPTION
		"The number of NATS present on this system."
	::= { nat 1 }

natTable OBJECT-TYPE
	SYNTAX SEQUENCE OF NatEntry
	MAX-ACCESS not-accessible
	STATUS current
	DESCRIPTION
		"A list of NAT entries. The number of
		entries is given by the value of natNumber."
	::= { nat 2 }

natEntry OBJECT-TYPE
	SYNTAX NatEntry
	MAX-ACCESS not-accessible
	STATUS current
	DESCRIPTION
		"A NAT entry containing information by nat."
	INDEX { natIndex }
	::= { natTable 1 }

NatEntry ::=
	SEQUENCE {
		natIndex	INTEGER,
		natDescr	DisplayString,
		natIpAddrFR	IpAddress,
		natIpAddrTO	IpAddress,
		natPktsin	Counter32,
		natPktsout	Counter32,
		natBitsin	Counter32,
		natBitsout	Counter32,
		natPktsinHi32	Counter32,
		natPktsoutHi32	Counter32,
		natBitsinHi32	Counter32,
		natBitsoutHi32	Counter32,
		natOutsideNetmask IpAddress,
		natOutsideBroadcast IpAddress,
		natInterface	DisplayString, -- This has been deprecated 
		natUnitId	INTEGER,
		natVLANs	DisplayString,
		natARPEnabled	INTEGER,
		natEnabled	INTEGER,
		natHCPktsin	Counter64,
		natHCPktsout	Counter64,
		natHCBitsin	Counter64,
		natHCBitsout	Counter64
	}

natIndex OBJECT-TYPE
	SYNTAX INTEGER (0..65535)
	MAX-ACCESS read-only
	STATUS current
	DESCRIPTION
		"A unique value for each NAT defined."
	::= { natEntry 1 }

natDescr OBJECT-TYPE
	SYNTAX DisplayString (SIZE (0..255))
	MAX-ACCESS read-only
	STATUS current
	DESCRIPTION
		"A textual string describing the NAT."
	::= { natEntry 2 }

natIpAddrFR OBJECT-TYPE
	SYNTAX IpAddress
	MAX-ACCESS read-only
	STATUS current
	DESCRIPTION
		"The FROM IP Address for the NAT."
	::= { natEntry 3 }

natIpAddrTO OBJECT-TYPE
	SYNTAX IpAddress
	MAX-ACCESS read-only
	STATUS current
	DESCRIPTION
		"The TO IP Address for the NAT."
	::= { natEntry 4 }

natPktsin OBJECT-TYPE
	SYNTAX Counter32
	MAX-ACCESS read-only
	STATUS current
	DESCRIPTION
		"The total packets in for this NAT."
	::= { natEntry 5 }

natPktsout OBJECT-TYPE
	SYNTAX Counter32
	MAX-ACCESS read-only
	STATUS current
	DESCRIPTION
		"The total packets out for this NAT."
	::= { natEntry 6 }

natBitsin OBJECT-TYPE
	SYNTAX Counter32
	MAX-ACCESS read-only
	STATUS current
	DESCRIPTION
		"The total bits in for this NAT."
	::= { natEntry 7 }

natBitsout OBJECT-TYPE
	SYNTAX Counter32
	MAX-ACCESS read-only
	STATUS current
	DESCRIPTION
		"The total bits out for this NAT."
	::= { natEntry 8 }

natPktsinHi32 OBJECT-TYPE
	SYNTAX Counter32
	MAX-ACCESS read-only
	STATUS current
	DESCRIPTION
		"The total packets in for this NAT."
	::= { natEntry 9 }

natPktsoutHi32 OBJECT-TYPE
	SYNTAX Counter32
	MAX-ACCESS read-only
	STATUS current
	DESCRIPTION
		"The total packets out for this NAT."
	::= { natEntry 10 }

natBitsinHi32 OBJECT-TYPE
	SYNTAX Counter32
	MAX-ACCESS read-only
	STATUS current
	DESCRIPTION
		"The total bits in for this NAT."
	::= { natEntry 11 }

natBitsoutHi32 OBJECT-TYPE
	SYNTAX Counter32
	MAX-ACCESS read-only
	STATUS current
	DESCRIPTION
		"The total bits out for this NAT."
	::= { natEntry 12 }

natOutsideNetmask OBJECT-TYPE
	SYNTAX IpAddress
	MAX-ACCESS read-only
	STATUS current
	DESCRIPTION
		"The outside netmask for this NAT."
	::= { natEntry 13 }

natOutsideBroadcast OBJECT-TYPE
	SYNTAX IpAddress
	MAX-ACCESS read-only
	STATUS current
	DESCRIPTION
		"The outside broadcast address for this NAT."
	::= { natEntry 14 }

natInterface OBJECT-TYPE
	SYNTAX 	DisplayString (SIZE (0..255))
	MAX-ACCESS read-only
	STATUS deprecated
	DESCRIPTION
		"NATs now exist on VLANS and not specific interfaces. 
		This OID is deprecated and will always return 0.0.0.0."
	::= { natEntry 15 }

natUnitId OBJECT-TYPE
	SYNTAX 	INTEGER
	MAX-ACCESS read-only
	STATUS current
	DESCRIPTION
		"The unit id associated with this NAT."
	::= { natEntry 16 }

natVLANs OBJECT-TYPE
	SYNTAX 	DisplayString (SIZE (0..255))
	MAX-ACCESS read-only
	STATUS current
	DESCRIPTION
		"If this list is empty, (the default) this NAT  will be accessible on all VLANS.
		If this list is not empty, this NAT will be accessible only on those VLANs
		specified in the list."
	::= { natEntry 17 }

natARPEnabled OBJECT-TYPE
	SYNTAX 	INTEGER {
		true(1),
		false(2)
	}
	MAX-ACCESS read-only
	STATUS current
	DESCRIPTION
		"States whether the NAT can send ARP requests;
		true = yes, false = no."
	::= { natEntry 18 }

natEnabled OBJECT-TYPE
	SYNTAX 	INTEGER {
		true(1),
		false(2)
	}
	MAX-ACCESS read-only
	STATUS current
	DESCRIPTION
		"States whether the NAT is enabled; true = enabled,
		false = disabled."
	::= { natEntry 19 }

natHCPktsin OBJECT-TYPE
	SYNTAX Counter64
	MAX-ACCESS read-only
	STATUS current
	DESCRIPTION
		"The total packets in for this NAT."
	::= { natEntry 20 }

natHCPktsout OBJECT-TYPE
	SYNTAX Counter64
	MAX-ACCESS read-only
	STATUS current
	DESCRIPTION
		"The total packets out for this NAT."
	::= { natEntry 21 }

natHCBitsin OBJECT-TYPE
	SYNTAX Counter64
	MAX-ACCESS read-only
	STATUS current
	DESCRIPTION
		"The total bits in for this NAT."
	::= { natEntry 22 }

natHCBitsout OBJECT-TYPE
	SYNTAX Counter64
	MAX-ACCESS read-only
	STATUS current
	DESCRIPTION
		"The total bits out for this NAT."
	::= { natEntry 23 }

--================================================================
-- VPORT information
--================================================================
vportNumber OBJECT-TYPE
	SYNTAX INTEGER
	MAX-ACCESS read-only
	STATUS current
	DESCRIPTION
		"The number of virtual ports present on this system."
	::= { vport 1 }

vportTable OBJECT-TYPE
	SYNTAX SEQUENCE OF VportEntry
	MAX-ACCESS not-accessible
	STATUS current
	DESCRIPTION
		"A list of virtual port entries. The number of
entries is given by the value of vportNumber."
	::= { vport 2 }

vportEntry OBJECT-TYPE
	SYNTAX VportEntry
	MAX-ACCESS not-accessible
	STATUS current
	DESCRIPTION
		"A virtual port entry containing virtual port statistics."
	INDEX { vportIndex }
	::= { vportTable 1 }

VportEntry ::=
	SEQUENCE {
		vportIndex	INTEGER,
		vportPort	INTEGER,
		vportDescr	DisplayString,
		vportPktsin	Counter32,
		vportPktsout	Counter32,
		vportBitsin	Counter32,
		vportBitsout	Counter32,
		vportConcur	INTEGER,
		vportConmax	INTEGER,
		vportConlimit	INTEGER,
		vportContot	Counter32,
		vportReaped	Counter32,
		vportPktsinHi32	Counter32,
		vportPktsoutHi32	Counter32,
		vportBitsinHi32	Counter32,
		vportBitsoutHi32	Counter32,
		vportAllowed	INTEGER,
		vportTCPpersistence	INTEGER,
		vportUDPpersistence	INTEGER,
		vportIPpersistence	INTEGER,
		vportUDPEnabled		TruthValue,
		vportHCPktsin	Counter64,
		vportHCPktsout	Counter64,
		vportHCBitsin	Counter64,
		vportHCBitsout	Counter64
	}

vportIndex OBJECT-TYPE
	SYNTAX INTEGER (0..65535)
	MAX-ACCESS read-only
	STATUS current
	DESCRIPTION
		"A unique value for each virtual port defined."
	::= { vportEntry 1 }

vportPort OBJECT-TYPE
	SYNTAX INTEGER
	MAX-ACCESS read-only
	STATUS current
	DESCRIPTION
		"The port Number for the virtual port."
	::= { vportEntry 2 }

vportDescr OBJECT-TYPE
	SYNTAX DisplayString (SIZE (0..255))
	MAX-ACCESS read-only
	STATUS current
	DESCRIPTION
		"A textual string describing the virtual port."
	::= { vportEntry 3 }

vportPktsin OBJECT-TYPE
	SYNTAX Counter32
	MAX-ACCESS read-only
	STATUS current
	DESCRIPTION
		"The total packets in for this virtual port."
	::= { vportEntry 4 }

vportPktsout OBJECT-TYPE
	SYNTAX Counter32
	MAX-ACCESS read-only
	STATUS current
	DESCRIPTION
		"The total packets out for this virtual port."
	::= { vportEntry 5 }

vportBitsin OBJECT-TYPE
	SYNTAX Counter32
	MAX-ACCESS read-only
	STATUS current
	DESCRIPTION
		"The total bits in for this virtual port."
	::= { vportEntry 6 }

vportBitsout OBJECT-TYPE
	SYNTAX Counter32
	MAX-ACCESS read-only
	STATUS current
	DESCRIPTION
		"The total bits out for this virtual port."
	::= { vportEntry 7 }

vportConcur OBJECT-TYPE
	SYNTAX INTEGER
	MAX-ACCESS read-only
	STATUS current
	DESCRIPTION
		"The number of current connections for this virtual
		port"
	::= { vportEntry 8 }

vportConmax OBJECT-TYPE
	SYNTAX INTEGER
	MAX-ACCESS read-only
	STATUS current
	DESCRIPTION
		"The maximum number of connections this virtual port
		has had open at any one time."
	::= { vportEntry 9 }

vportConlimit OBJECT-TYPE
	SYNTAX INTEGER
	MAX-ACCESS read-only
	STATUS current
	DESCRIPTION
		"The connection limit for this virtual port."
	::= { vportEntry 10 }

vportContot OBJECT-TYPE
	SYNTAX Counter32
	MAX-ACCESS read-only
	STATUS current
	DESCRIPTION
		"The total number of connections this virtual port
		has had open since the server started."
	::= { vportEntry 11 }

vportReaped OBJECT-TYPE
	SYNTAX Counter32
	MAX-ACCESS read-only
	STATUS current
	DESCRIPTION
		"The total connections reaped on this virtual port."
	::= { vportEntry 12 }

vportPktsinHi32 OBJECT-TYPE
	SYNTAX Counter32
	MAX-ACCESS read-only
	STATUS current
	DESCRIPTION
		"The total packets in for this virtual port."
	::= { vportEntry 13 }

vportPktsoutHi32 OBJECT-TYPE
	SYNTAX Counter32
	MAX-ACCESS read-only
	STATUS current
	DESCRIPTION
		"The total packets out for this virtual port."
	::= { vportEntry 14 }

vportBitsinHi32 OBJECT-TYPE
	SYNTAX Counter32
	MAX-ACCESS read-only
	STATUS current
	DESCRIPTION
		"The total bits in for this virtual port."
	::= { vportEntry 15 }

vportBitsoutHi32 OBJECT-TYPE
	SYNTAX Counter32
	MAX-ACCESS read-only
	STATUS current
	DESCRIPTION
		"The total bits out for this virtual port."
	::= { vportEntry 16 }

vportAllowed OBJECT-TYPE
	SYNTAX INTEGER { allowed(1), disallowed(2) }
	MAX-ACCESS read-only
	STATUS current
	DESCRIPTION "Is TCP access allowed for this port?"
	::= { vportEntry 17 }

vportTCPpersistence OBJECT-TYPE
	SYNTAX INTEGER
	MAX-ACCESS read-only
	STATUS current
	DESCRIPTION "Number of seconds before TCP persistence
		expires for this virtual port."
	::= { vportEntry 18 }

vportUDPpersistence OBJECT-TYPE
	SYNTAX INTEGER
	MAX-ACCESS read-only
	STATUS current
	DESCRIPTION "Number of seconds before UDP persistence
		expires for this virtual port."
	::= { vportEntry 19 }

vportIPpersistence OBJECT-TYPE
	SYNTAX INTEGER
	MAX-ACCESS read-only
	STATUS current
	DESCRIPTION "Number of seconds before IP persistence
		expires for this virtual port."
	::= { vportEntry 20 }

vportUDPEnabled OBJECT-TYPE
	SYNTAX TruthValue
	MAX-ACCESS read-only
	STATUS current
	DESCRIPTION "States whether the UDP access to this port 
	is enabled for this port; true = enabled, false = disabled."
	::= { vportEntry 21 }

vportHCPktsin OBJECT-TYPE
	SYNTAX Counter64
	MAX-ACCESS read-only
	STATUS current
	DESCRIPTION
		"The total packets in for this virtual port."
	::= { vportEntry 22 }

vportHCPktsout OBJECT-TYPE
	SYNTAX Counter64
	MAX-ACCESS read-only
	STATUS current
	DESCRIPTION
		"The total packets out for this virtual port."
	::= { vportEntry 23 }

vportHCBitsin OBJECT-TYPE
	SYNTAX Counter64
	MAX-ACCESS read-only
	STATUS current
	DESCRIPTION
		"The total bits in for this virtual port."
	::= { vportEntry 24 }

vportHCBitsout OBJECT-TYPE
	SYNTAX Counter64
	MAX-ACCESS read-only
	STATUS current
	DESCRIPTION
		"The total bits out for this virtual port."
	::= { vportEntry 25 }



--================================================================
-- MEMBER information
-- member information is indexed by Virtual Path and Ordinal Number
--================================================================

memberTable OBJECT-TYPE
	SYNTAX SEQUENCE OF MemberEntry
	MAX-ACCESS not-accessible
	STATUS current
	DESCRIPTION
		"A table containing balancer member information."
	::= { member 2 }

memberEntry OBJECT-TYPE
	SYNTAX MemberEntry
	MAX-ACCESS not-accessible
	STATUS current
	DESCRIPTION
		"Information Specific to Members."
	INDEX { memberVirtualAddress, memberVirtualAddressPort, 
		memberOrdinal }
	::= { memberTable 1 }

MemberEntry ::=
	SEQUENCE {
		memberVirtualAddress		IpAddress,
		memberVirtualAddressPort	INTEGER,
		memberOrdinal			INTEGER, 
		memberAddress			IpAddress,
		memberPort			INTEGER,
		memberStatus			INTEGER,
		memberPktsin			Counter32,
		memberPktsout			Counter32,
		memberBitsin			Counter32,
		memberBitsout			Counter32,
		memberConcur			INTEGER,
		memberConmax			INTEGER,
		memberConlimit			INTEGER,
		memberContot			Counter32,
		memberPktsinHi32		Counter32,
		memberPktsoutHi32		Counter32,
		memberBitsinHi32		Counter32,
		memberBitsoutHi32		Counter32,
		memberHCPktsin			Counter64,
		memberHCPktsout			Counter64,
		memberHCBitsin			Counter64,
		memberHCBitsout			Counter64
	}

memberVirtualAddress OBJECT-TYPE
	SYNTAX IpAddress
	MAX-ACCESS read-only
	STATUS current
	DESCRIPTION
		"The virtual IP address."
	::= { memberEntry 1 }

memberVirtualAddressPort OBJECT-TYPE
	SYNTAX INTEGER (0..65535)
	MAX-ACCESS read-only
	STATUS current
	DESCRIPTION
		"The virtual IP address port."
	::= { memberEntry 2 }

memberOrdinal OBJECT-TYPE
	SYNTAX INTEGER (0..65535)
	MAX-ACCESS read-only
	STATUS current
	DESCRIPTION
		"The virtual IP address member ordinal number."
	::= { memberEntry 3 }

memberAddress OBJECT-TYPE
	SYNTAX IpAddress
	MAX-ACCESS read-only
	STATUS current
	DESCRIPTION
		"The node IP address for this member."
	::= { memberEntry 4 }

memberPort OBJECT-TYPE
	SYNTAX INTEGER
	MAX-ACCESS read-only
	STATUS current
	DESCRIPTION
		"The node port for this member."
	::= { memberEntry 5 }

memberStatus OBJECT-TYPE
	SYNTAX BigAPIStatus
	MAX-ACCESS read-only
	STATUS current
	DESCRIPTION
		"The status of this member."
	::= { memberEntry 6 }

memberPktsin OBJECT-TYPE
	SYNTAX Counter32
	MAX-ACCESS read-only
	STATUS current
	DESCRIPTION
		"The count of packets read off the network for
		this member."
	::= { memberEntry 7 }

memberPktsout OBJECT-TYPE
	SYNTAX Counter32
	MAX-ACCESS read-only
	STATUS current
	DESCRIPTION
		"The count of packets written to the network for
		this member."
	::= { memberEntry 8 }

memberBitsin OBJECT-TYPE
	SYNTAX Counter32
	MAX-ACCESS read-only
	STATUS current
	DESCRIPTION
		"The count of bits read off the network for this
		member."
	::= { memberEntry 9 }

memberBitsout OBJECT-TYPE
	SYNTAX Counter32
	MAX-ACCESS read-only
	STATUS current
	DESCRIPTION
		"The count of bits written to the network for
		this member."
	::= { memberEntry 10 }

memberConcur OBJECT-TYPE
	SYNTAX INTEGER
	MAX-ACCESS read-only
	STATUS current
	DESCRIPTION
		"The number of connections currently open for this
		member."
	::= { memberEntry 11 }

memberConmax OBJECT-TYPE
	SYNTAX INTEGER
	MAX-ACCESS read-only
	STATUS current
	DESCRIPTION
		"The maximum number of connections this member has had
		open at any one time."
	::= { memberEntry 12 }

memberConlimit OBJECT-TYPE
	SYNTAX INTEGER
	MAX-ACCESS read-only
	STATUS current
	DESCRIPTION
		"The total number of connections this member can
		support at one time."
	::= { memberEntry 13 }

memberContot OBJECT-TYPE
	SYNTAX Counter32
	MAX-ACCESS read-only
	STATUS current
	DESCRIPTION
		"The total number of connections this member has
		served since the server started."
	::= { memberEntry 14 }

memberPktsinHi32 OBJECT-TYPE
	SYNTAX Counter32
	MAX-ACCESS read-only
	STATUS current
	DESCRIPTION
		"The count of packets read off the network for
		this member."
	::= { memberEntry 15 }

memberPktsoutHi32 OBJECT-TYPE
	SYNTAX Counter32
	MAX-ACCESS read-only
	STATUS current
	DESCRIPTION
		"The count of packets written to the network for
		this member."
	::= { memberEntry 16 }

memberBitsinHi32 OBJECT-TYPE
	SYNTAX Counter32
	MAX-ACCESS read-only
	STATUS current
	DESCRIPTION
		"The count of bits read off the network for this
		member."
	::= { memberEntry 17 }

memberBitsoutHi32 OBJECT-TYPE
	SYNTAX Counter32
	MAX-ACCESS read-only
	STATUS current
	DESCRIPTION
		"The count of bits written to the network for
		this member."
	::= { memberEntry 18 }

memberHCPktsin OBJECT-TYPE
	SYNTAX Counter64
	MAX-ACCESS read-only
	STATUS current
	DESCRIPTION
		"The count of packets read off the network for
		this member."
	::= { memberEntry 19 }

memberHCPktsout OBJECT-TYPE
	SYNTAX Counter64
	MAX-ACCESS read-only
	STATUS current
	DESCRIPTION
		"The count of packets written to the network for
		this member."
	::= { memberEntry 20 }

memberHCBitsin OBJECT-TYPE
	SYNTAX Counter64
	MAX-ACCESS read-only
	STATUS current
	DESCRIPTION
		"The count of bits read off the network for this
		member."
	::= { memberEntry 21 }

memberHCBitsout OBJECT-TYPE
	SYNTAX Counter64
	MAX-ACCESS read-only
	STATUS current
	DESCRIPTION
		"The count of bits written to the network for
		this member."
	::= { memberEntry 22 }

--================================================================
-- Node information
--================================================================
nodesNumber OBJECT-TYPE
	SYNTAX INTEGER
	MAX-ACCESS read-only
	STATUS current
	DESCRIPTION
		"The number of Nodes present on this system."
	::= { nodes 1 }

nodesTable OBJECT-TYPE
	SYNTAX SEQUENCE OF NodesEntry
	MAX-ACCESS not-accessible
	STATUS current
	DESCRIPTION
		"A list of Nodes entries. The number of entries is
		given by the value of nodesNumber."
	::= { nodes 2 }

nodesEntry OBJECT-TYPE
	SYNTAX NodesEntry
	MAX-ACCESS not-accessible
	STATUS current
	DESCRIPTION
		"A ndaddr entry containing ndaddr statistics."
	INDEX { nodesIndex }
	::= { nodesTable 1 }

NodesEntry ::=
	SEQUENCE {
		nodesIndex		INTEGER,
		nodesAddr		DisplayString,
		nodesPktsinLo32		Counter32,
		nodesPktsinHi32		Counter32,
		nodesPktsoutLo32	Counter32,
		nodesPktsoutHi32	Counter32,
		nodesBitsinLo32		Counter32,
		nodesBitsinHi32		Counter32,
		nodesBitsoutLo32	Counter32,
		nodesBitsoutHi32	Counter32,
		nodesCurrentConnections	INTEGER,
		nodesMaximumConnections INTEGER,
		nodesConnectionLimit	INTEGER,
		nodesTotalConnections	Counter32,
		nodesEnabled		INTEGER,
		nodesPingerState	INTEGER,
		nodesHCPktsin		Counter64,
		nodesHCPktsout		Counter64,
		nodesHCBitsin		Counter64,
		nodesHCBitsout		Counter64
	}

nodesIndex OBJECT-TYPE
	SYNTAX INTEGER (0..65535)
	MAX-ACCESS read-only
	STATUS current
	DESCRIPTION
		"A unique value for each nodes defined."
	::= { nodesEntry 1 }

nodesAddr OBJECT-TYPE
	SYNTAX DisplayString (SIZE (0..255))
	MAX-ACCESS read-only
	STATUS current
	DESCRIPTION
		"The IP Address and Port of the Node."
	::= { nodesEntry 2 }

nodesPktsinLo32 OBJECT-TYPE
	SYNTAX Counter32
	MAX-ACCESS read-only
	STATUS current
	DESCRIPTION
		"The low 32 bits of the number of packets delivered to this Node."
	::= { nodesEntry 3 }

nodesPktsinHi32 OBJECT-TYPE
	SYNTAX Counter32
	MAX-ACCESS read-only
	STATUS current
	DESCRIPTION
		"The high 32 bits of the number of packets delivered to this Node."
	::= { nodesEntry 4 }

nodesPktsoutLo32 OBJECT-TYPE
	SYNTAX Counter32
	MAX-ACCESS read-only
	STATUS current
	DESCRIPTION
		"The low 32 bits of the number of packets delivered from this Node."
	::= { nodesEntry 5 }

nodesPktsoutHi32 OBJECT-TYPE
	SYNTAX Counter32
	MAX-ACCESS read-only
	STATUS current
	DESCRIPTION
		"The high 32 bits of the number of packets delivered from this Node."
	::= { nodesEntry 6 }

nodesBitsinLo32 OBJECT-TYPE
	SYNTAX Counter32
	MAX-ACCESS read-only
	STATUS current
	DESCRIPTION
		"The low 32 bits of the number of bits delivered to this Node."
	::= { nodesEntry 7}

nodesBitsinHi32 OBJECT-TYPE
	SYNTAX Counter32
	MAX-ACCESS read-only
	STATUS current
	DESCRIPTION
		"The high 32 bits of the number of bits delivered to this Node."
	::= { nodesEntry 8 }

nodesBitsoutLo32 OBJECT-TYPE
	SYNTAX Counter32
	MAX-ACCESS read-only
	STATUS current
	DESCRIPTION
		"The low 32 bits of the number of bits delivered from this Node."
	::= { nodesEntry 9 }

nodesBitsoutHi32 OBJECT-TYPE
	SYNTAX Counter32
	MAX-ACCESS read-only
	STATUS current
	DESCRIPTION
		"The high 32 bits of the number of bits delivered from this Node."
	::= { nodesEntry 10 }

nodesCurrentConnections OBJECT-TYPE
	SYNTAX INTEGER
	MAX-ACCESS read-only
	STATUS current
	DESCRIPTION
		"The number of current connections for this Node."
	::= { nodesEntry 11 }

nodesMaximumConnections OBJECT-TYPE
	SYNTAX INTEGER
	MAX-ACCESS read-only
	STATUS current
	DESCRIPTION
		"The maximum number of connections this Node
		has had open at one time."
	::= { nodesEntry 12 }

nodesConnectionLimit OBJECT-TYPE
	SYNTAX INTEGER
	MAX-ACCESS read-only
	STATUS current
	DESCRIPTION
		"The maximum number of connections this Node
		is allowed to have open at one time."
	::= { nodesEntry 13 }

nodesTotalConnections OBJECT-TYPE
	SYNTAX Counter32
	MAX-ACCESS read-only
	STATUS current
	DESCRIPTION
		"The total connections that this Node had
		had."
	::= { nodesEntry 14 }

nodesEnabled OBJECT-TYPE
	SYNTAX INTEGER {
		true(1),
		false(2)
	}
	MAX-ACCESS read-only
	STATUS current
	DESCRIPTION
		"States whether this Node is enabled;
		true = enabled, false = disabled."
	::= { nodesEntry 15 }

nodesPingerState OBJECT-TYPE
	SYNTAX INTEGER {
		unchecked(1),
		up(2),
		down(3),
		forcedDown(4),
		checking(5)
	}
	MAX-ACCESS read-only
	STATUS current
	DESCRIPTION
		"Enumerated type, describing Node state, up, down 
                 checking, unchecked."
	::= { nodesEntry 16 }

nodesHCPktsin OBJECT-TYPE
	SYNTAX Counter64
	MAX-ACCESS read-only
	STATUS current
	DESCRIPTION
		"The number of packets delivered to this Node."
	::= { nodesEntry 17 }

nodesHCPktsout OBJECT-TYPE
	SYNTAX Counter64
	MAX-ACCESS read-only
	STATUS current
	DESCRIPTION
		"The number of packets delivered from this Node."
	::= { nodesEntry 18 }

nodesHCBitsin OBJECT-TYPE
	SYNTAX Counter64
	MAX-ACCESS read-only
	STATUS current
	DESCRIPTION
		"The number of bits delivered to this Node."
	::= { nodesEntry 19 }

nodesHCBitsout OBJECT-TYPE
	SYNTAX Counter64
	MAX-ACCESS read-only
	STATUS current
	DESCRIPTION
		"The number of bits delivered from this Node."
	::= { nodesEntry 20 }

--================================================================
-- TRAP Information
--================================================================
loadBalTrapMessage OBJECT-TYPE
	SYNTAX DisplayString (SIZE (0..255))
	MAX-ACCESS read-only
	STATUS current
	DESCRIPTION
		"Text string which describes addtional information for a load balance trap."
	::= { loadBalTrapMsgs 1 }

loadBalTrapIPString OBJECT-TYPE
	SYNTAX DisplayString (SIZE (0..255))
	MAX-ACCESS read-only
	STATUS current
	DESCRIPTION
		"Text string which describes an IP address."
	::= { loadBalTrapMsgs 2 }

loadBalTrapPort OBJECT-TYPE
	SYNTAX INTEGER 
	MAX-ACCESS read-only
	STATUS current
	DESCRIPTION
		"Text string which describes a port."
	::= { loadBalTrapMsgs 3 }
--=========================================================
loadBalTrapServiceDown NOTIFICATION-TYPE
	STATUS	current
	DESCRIPTION
		"Service came down."
	::= { loadBalTraps 2 }

loadBalTrapServiceUP NOTIFICATION-TYPE
	STATUS	current
	DESCRIPTION
		"Service came up."
	::= { loadBalTraps 3 }

loadBalTrapReset NOTIFICATION-TYPE
	STATUS	current
	DESCRIPTION
		"System reset."
	::= { loadBalTraps 4 }

loadBalTrapDenial NOTIFICATION-TYPE
	STATUS	current
	DESCRIPTION
		"Request is denied."
	::= { loadBalTraps 5 }

loadBalTrapLogin NOTIFICATION-TYPE
	STATUS	current
	DESCRIPTION
		"Root login."
	::= { loadBalTraps 6 }

loadBalTrapRemoveUnit NOTIFICATION-TYPE
	STATUS	current
	DESCRIPTION
		"Removing unit. Potential failover of this BIG-IP."
	::= { loadBalTraps 7 }

loadBalTrapAddUnit NOTIFICATION-TYPE
	STATUS	current
	DESCRIPTION
		"Adding unit. This BIG-IP has taken responsibility for a new unit id."
	::= { loadBalTraps 8 }

loadBalTrapSysCrash NOTIFICATION-TYPE
	STATUS	current
	DESCRIPTION
		"The system has unexpectedly crashed. Call support."
	::= { loadBalTraps 9 }

loadBalTrapSysUnstable NOTIFICATION-TYPE
	STATUS	current
	DESCRIPTION
		"The system is not stable."
	::= { loadBalTraps 10 }

loadBalTrapNoPort NOTIFICATION-TYPE
	STATUS	current
	DESCRIPTION
		"No ports are avaiable on the system for TCP connection."
	::= { loadBalTraps 11 }

loadBalTrapSysPanic NOTIFICATION-TYPE
	STATUS	current
	DESCRIPTION
		"The system is panic. Call support."
	::= { loadBalTraps 19 }

loadBalTrapIntermitTraffic NOTIFICATION-TYPE
	STATUS	current
	DESCRIPTION
		"Intermittent traffic is detected. Check network."
	::= { loadBalTraps 20 }

loadBalTrapMemLow NOTIFICATION-TYPE
	STATUS	current
	DESCRIPTION
		"Memory is low on the system."
	::= { loadBalTraps 23 }

loadBalTrapNoMem NOTIFICATION-TYPE
	STATUS	current
	DESCRIPTION
		"The system can not allocate memory."
	::= { loadBalTraps 24 }

loadBalTrapWarn NOTIFICATION-TYPE
	STATUS	current
	DESCRIPTION
		"Warning condition is detected. Check logs."
	::= { loadBalTraps 25 }

loadBalTrapBigdFail NOTIFICATION-TYPE
	STATUS	current
	DESCRIPTION
		"Bigd is failure because of no memory."
	::= { loadBalTraps 28 }

loadBalTrapBigdServiceFail NOTIFICATION-TYPE
	STATUS	current
	DESCRIPTION
		"Bigd service checking is failure."
	::= { loadBalTraps 29 }

loadBalTrapProxydRestart NOTIFICATION-TYPE
	STATUS	current
	DESCRIPTION
		"Proxyd is restarted."
	::= { loadBalTraps 30 }

loadBalTrapAuthFail NOTIFICATION-TYPE
	STATUS	current
	DESCRIPTION
		"Authorization is not successful."
	::= { loadBalTraps 31 }

loadBalTrapUnkownUser NOTIFICATION-TYPE
	STATUS	current
	DESCRIPTION
		"Illegal user is trying to login, failed."
	::= { loadBalTraps 32 }

loadBalTrapBadSu NOTIFICATION-TYPE
	STATUS	current
	DESCRIPTION
		"Unauthorized attempt to switch user."
	::= { loadBalTraps 33 }

loadBalTrapNodeDown NOTIFICATION-TYPE
	OBJECTS {loadBalTrapIPString, loadBalTrapPortString}
	STATUS	current
	DESCRIPTION
		"A node is detected down."
	::= { loadBalTraps 34 }

loadBalTrapNodeUp NOTIFICATION-TYPE
	OBJECTS {loadBalTrapIPString, loadBalTrapPortString}
	STATUS	current
	DESCRIPTION
		"A node is detected up."
	::= { loadBalTraps 35 }

loadBalTrapNoNode NOTIFICATION-TYPE
	STATUS	current
	DESCRIPTION
		"There is no node available for vip."
	::= { loadBalTraps 36 }

loadBalTrapLicFail NOTIFICATION-TYPE
	STATUS	current
	DESCRIPTION
		"License authorization is failed."
	::= { loadBalTraps 37 }

loadBalTrapLoginFail NOTIFICATION-TYPE
	STATUS	current
	DESCRIPTION
		"Login is failed."
	::= { loadBalTraps 38 }

loadBalTrapStandby NOTIFICATION-TYPE
	STATUS	current
	DESCRIPTION
		"The unit is set to standby mode."
	::= { loadBalTraps 40 }

loadBalTrapActive  NOTIFICATION-TYPE
	STATUS	current
	DESCRIPTION
		"The unit is set to active mode."
	::= { loadBalTraps 41 }

loadBalTrapBigpipeLoadConfig  NOTIFICATION-TYPE
	STATUS	current
	DESCRIPTION
		"The configuration files are loaded."
	::= { loadBalTraps 42 }

loadBalTrapLoginFrom  NOTIFICATION-TYPE
	STATUS	current
	DESCRIPTION
		"Where the login is made from."
	::= { loadBalTraps 43 }

loadBalTrapReboot  NOTIFICATION-TYPE
	STATUS	current
	DESCRIPTION
		"The system is rebooted."
	::= { loadBalTraps 44 }

loadBalTrapNoRouteToHost  NOTIFICATION-TYPE
	STATUS	current
	DESCRIPTION
		"There is no route to the host."
	::= { loadBalTraps 45 }

loadBalTrapNoRouteToNode  NOTIFICATION-TYPE
	STATUS	current
	DESCRIPTION
		"There is no route to the node."
	::= { loadBalTraps 46 }

loadBalTrapInternalErr  NOTIFICATION-TYPE
	STATUS	current
	DESCRIPTION
		"There are some internal errors."
	::= { loadBalTraps 47 }

loadBalTrapLicFile  NOTIFICATION-TYPE
	STATUS	current
	DESCRIPTION
		"License file may be corrupted on the system."
	::= { loadBalTraps 49 }

loadBalTrapDupIP  NOTIFICATION-TYPE
	STATUS	current
	DESCRIPTION
		"There are duplication IP addresses on the system."
	::= { loadBalTraps 50 }

loadBalTrapSshFail  NOTIFICATION-TYPE
	STATUS	current
	DESCRIPTION
		"There are too many authentication failures for ssh, deny."
	::= { loadBalTraps 52 }

loadBalTrapSshPassFail  NOTIFICATION-TYPE
	STATUS	current
	DESCRIPTION
		"Wrong password for ssh , deny."
	::= { loadBalTraps 53 }

loadBalTrapVIPAdd  NOTIFICATION-TYPE
	STATUS	current
	DESCRIPTION
		"A virtual IP is added."
	::= { loadBalTraps 62 }

loadBalTrapVIPRedefine  NOTIFICATION-TYPE
	STATUS	current
	DESCRIPTION
		"A virtual IP is redefined."
	::= { loadBalTraps 63 }

loadBalTrapSNATAdd  NOTIFICATION-TYPE
	STATUS	current
	DESCRIPTION
		"SNAT is added."
	::= { loadBalTraps 64 }

loadBalTrapNATDefine  NOTIFICATION-TYPE
	STATUS	current
	DESCRIPTION
		"NAT is defined."
	::= { loadBalTraps 65 }

loadBalTrapNoNAT  NOTIFICATION-TYPE
	STATUS	current
	DESCRIPTION
		"No NAT is defined."
	::= { loadBalTraps 68 }

loadBalTrapNoNATTranslate  NOTIFICATION-TYPE
	STATUS	current
	DESCRIPTION
		"Can not tranalte NAT."
	::= { loadBalTraps 70 }

loadBalTrapUnitNotReady  NOTIFICATION-TYPE
	STATUS	current
	DESCRIPTION
		"The unit is not ready."
	::= { loadBalTraps 72 }

loadBalTrapNeedUpgrade  NOTIFICATION-TYPE
	STATUS	current
	DESCRIPTION
		"Upgrade is needed."
	::= { loadBalTraps 73 }

END
